FME workspace fn001_徒歩道をCityGML形式からMVT形式へ変換.fmw
Title: PLATEAU4 可視化用データ変換02 道路・鉄道・徒歩道・広場・航路
Description: Tech Preview
3D都市モデル標準製品仕様書第4.x版に基づいて作成された交通モデル (道路、鉄道、徒歩道、広場、航路) CityGML データセットを Mapbox Vector Tile (MVT) または Cesium 3D Tiles データセットに変換します。
[注1] このワークスペースによる変換を実行するには、「日本のジオイド2011」に基づく標高から楕円体高への変換用に、FME Hub "Vertical Transformation with GSIGEO2011" テンプレートに同梱されているグリッドファイルが必要です。
Vertical Transformation with GSIGEO2011  
https://hub.safe.com/publishers/pacific-spatial-solutions/templates/vertical-transformation-with-gsigeo2011
上記テンプレートを一旦 FME Workbench で開いてワークスペース (*.fmw) として保存すると、 "gsigeo2011.zip" というアーカイブが抽出、保存されます。 まず、これを解凍して展開される次の2ファイルをディスクシステムの適当な場所に保存してください。ここで、*.gdc ファイルから *.grd ファイルへの相対パスはこのまま維持しておく必要があることに注意してください。  
./gsigeo2011_ver2_2.gdc  
./griddata/gsigeo2011_ver2_2.grd  
可視化用データ変換ワークスペースを実行する際に、上記 "gsigeo2011_ver2_2.gdc" を Geoid Height Grid パラメーターに設定することにより、「日本のジオイド2011」に基づく標高から楕円体高への変換を行うことができます。
[注2] 広場モデルの交通領域、補助交通領域フィーチャーが xlink によって同じ都市モデルにおける道路モデルを参照している場合は、xlink:href 属性に記述されている場所に参照先の道路モデルデータファイルが 存在している必要があります。
History: 2024-12-13,Takashi Iijima, PSS,リリース,2024-12-15,Takashi Iijima, PSS,PLATEAU4.AttributeReader 更新,2024-12-21,Takashi Iijima, PSS,MVTレイヤ名とするフィーチャータイプ名から名前空間プレフィクスを削除,2024-12-22,Takashi Iijima, PSS,主題属性読込処理のパフォーマンス改善 #2,2024-12-23,Takashi Iijima, PSS,[Fix] フラットにした主題属性に間違った値が設定されるケースがあるという不具合を解消,2024-12-24,Takashi Iijima, PSS,主題属性の値のうち、整数として解釈できるが「0」から始まる文字列はそのまま文字列として読むように修正（例: xs:gYear型の不明値として定義されている"0001"）。,2025-01-07,Takashi Iijima, PSS,[Fix] 汎用属性セットが記述されている場合に生じるエラーの解消,2025-01-17,Takashi Iijima, PSS,数値属性で値が -9999, 9999 のものはフラットにしないように修正,2025-01-29,Takashi Iijima, PSS,[Fix] LOD0のフィーチャーが記述されている場合に生じるスキーマ定義に関するエラーを解消,2025-02-03,Takashi Iijima, PSS,[Fix] LOD2 TrafficArea と AuxiliaryTrafficArea がある場合に、AuxiliaryTrafficArea フィーチャーが出力先 MVT に書き込まれない不具合を修正,2025-02-16,Takashi iijima, PSS,[Fix] 道路の TraffixArea, AuxiliaryTraffixArea を参照している広場モデルのジオメトリが出力先 MVT に書き込まれない不具合を修正

Parameters:
- DATA_FILE = $(FME_MF_DIR)15202_nagaoka-shi_unif_echigo-hillside-park_2024_citygml_1/udx/trk/*.gml   # 3D都市モデルデータセット (道路,鉄道,徒歩道,広場,航路)
- CITY_CODE = 15202   # 市区町村コード (5桁数字)
- CITY_NAME = nagaoka-shi   # 市区町村英名
- DEST_ROOT_FOLDER = $(FME_MF_DIR)output/trk   # 変換結果出力先ルートフォルダー
- GRP_OPTIONS =   # オプション
- CODELISTS_FOLDER =   # codelists フォルダー
- SCHEMAS_FOLDER =   # schemas フォルダー
- GEOID_HEIGHT_GRID = $(FME_MF_DIR)resources/gsigeo2011/gsigeo2011_ver2_2.gdc   # Geoid Height Grid
- LOG_FILE =   # Log File
- DestDataset_CSV2 = $(FME_MF_DIR)output/trk   # Destination CSV (Comma Separated Value) Folder
- mvt_min_zoom = 8
- mvt_max_zoom = 16
- DICT_OF_ATTRS_TO_FLAT:   # フラット化属性 {接頭辞/地物型 : [ { 属性名, JSONパス, データ型 } ] }
      {
         "tran/tran:Road" : [
            {
               "attribute" : "gml:name",
               "json_path" : "gml:name",
               "data_type" : "buffer"
            },
            {
               "attribute" : "core:creationDate",
               "json_path" : "core:creationDate",
               "data_type" : "date"
            },
            {
               "attribute" : "tran:class",
               "json_path" : "tran:class",
               "data_type" : "buffer"
            },
            {
               "attribute" : "tran:function",
               "json_path" : "tran:function",
               "data_type" : "buffer"
            },
            {
               "attribute" : "tran:usage",
               "json_path" : "tran:usage",
               "data_type" : "buffer"
            },
            {
               "attribute" : "uro:RoadStructureAttribute_uro:widthType",
               "json_path" : "uro:RoadStructureAttribute uro:widthType",
               "data_type" : "buffer"
            },
            {
               "attribute" : "uro:RoadStructureAttribute_uro:width",
               "json_path" : "uro:RoadStructureAttribute uro:width",
               "data_type" : "real64"
            },
            {
               "attribute" : "uro:RoadStructureAttribute_uro:numberOfLanes",
               "json_path" : "uro:RoadStructureAttribute uro:numberOfLanes",
               "data_type" : "int16"
            },
            {
               "attribute" : "uro:RoadStructureAttribute_uro:sectionType",
               "json_path" : "uro:RoadStructureAttribute uro:sectionType",
               "data_type" : "buffer"
            },
            {
               "attribute" : "uro:TrafficVolumeAttribute_uro:sectionID",
               "json_path" : "uro:TrafficVolumeAttribute uro:sectionID",
               "data_type" : "buffer"
            },
            {
               "attribute" : "uro:TrafficVolumeAttribute_uro:routeName",
               "json_path" : "uro:TrafficVolumeAttribute uro:routeName",
               "data_type" : "buffer"
            },
            {
               "attribute" : "uro:TrafficVolumeAttribute_uro:weekday12hourTrafficVolume",
               "json_path" : "uro:TrafficVolumeAttribute uro:weekday12hourTrafficVolume",
               "data_type" : "real64"
            },
            {
               "attribute" : "uro:TrafficVolumeAttribute_uro:weekday24hourTrafficVolume",
               "json_path" : "uro:TrafficVolumeAttribute uro:weekday24hourTrafficVolume",
               "data_type" : "real64"
            },
            {
               "attribute" : "uro:TrafficVolumeAttribute_uro:largeVehicleRate",
               "json_path" : "uro:TrafficVolumeAttribute uro:largeVehicleRate",
               "data_type" : "real64"
            },
            {
               "attribute" : "uro:TrafficVolumeAttribute_uro:congestionRate",
               "json_path" : "uro:TrafficVolumeAttribute uro:congestionRate",
               "data_type" : "real64"
            },
            {
               "attribute" : "uro:TrafficVolumeAttribute_uro:averageTravelSpeedInCongestion",
               "json_path" : "uro:TrafficVolumeAttribute uro:averageTravelSpeedInCongestion",
               "data_type" : "real64"
            },
            {
               "attribute" : "uro:TrafficVolumeAttribute_uro:averageInboundTravelSpeedInCongestion",
               "json_path" : "uro:TrafficVolumeAttribute uro:averageInboundTravelSpeedInCongestion",
               "data_type" : "real64"
            },
            {
               "attribute" : "uro:TrafficVolumeAttribute_uro:averageOutboundTravelSpeedInCongestion",
               "json_path" : "uro:TrafficVolumeAttribute uro:averageOutboundTravelSpeedInCongestion",
               "data_type" : "real64"
            },
            {
               "attribute" : "uro:TrafficVolumeAttribute_uro:averageInboundTravelSpeedNotCongestion",
               "json_path" : "uro:TrafficVolumeAttribute uro:averageInboundTravelSpeedNotCongestion",
               "data_type" : "real64"
            },
            {
               "attribute" : "uro:TrafficVolumeAttribute_uro:averageOutboundTravelSpeedNotCongestion",
               "json_path" : "uro:TrafficVolumeAttribute uro:averageOutboundTravelSpeedNotCongestion",
               "data_type" : "real64"
            },
            {
               "attribute" : "uro:TrafficVolumeAttribute_uro:observationPointName",
               "json_path" : "uro:TrafficVolumeAttribute uro:observationPointName",
               "data_type" : "buffer"
            },
            {
               "attribute" : "uro:TrafficVolumeAttribute_uro:reference",
               "json_path" : "uro:TrafficVolumeAttribute uro:reference",
               "data_type" : "buffer"
            },
            {
               "attribute" : "uro:TrafficVolumeAttribute_uro:surveyYear",
               "json_path" : "uro:TrafficVolumeAttribute uro:surveyYear",
               "data_type" : "int16"
            },
            {
               "attribute" : "uro:geometrySrcDescLod1",
               "json_path" : "uro:DataQualityAttribute uro:geometrySrcDescLod1",
               "data_type" : "buffer"
            },
            {
               "attribute" : "uro:lodType",
               "json_path" : "uro:DataQualityAttribute uro:lodType",
               "data_type" : "buffer"
            }
         ],
         "tran/tran:TrafficArea" : [
            {
               "attribute" : "gml:name",
               "json_path" : "ancestors gml:name",
               "data_type" : "buffer"
            },
            {
               "attribute" : "core:creationDate",
               "json_path" : "ancestors core:creationDate",
               "data_type" : "date"
            },
            {
               "attribute" : "tran:class",
               "json_path" : "ancestors tran:class",
               "data_type" : "buffer"
            },
            {
               "attribute" : "tran:Road_tran:function",
               "json_path" : "ancestors tran:function",
               "data_type" : "buffer"
            },
            {
               "attribute" : "tran:function",
               "json_path" : "tran:function",
               "data_type" : "buffer"
            },
            {
               "attribute" : "uro:numberOfLanes",
               "json_path" : "uro:TrafficAreaStructureAttribute uro:numberOfLanes",
               "data_type" : "int16"
            },
            {
               "attribute" : "tran:usage",
               "json_path" : "ancestors tran:usage",
               "data_type" : "buffer"
            },
            {
               "attribute" : "uro:RoadStructureAttribute_uro:widthType",
               "json_path" : "ancestors uro:RoadStructureAttribute uro:widthType",
               "data_type" : "buffer"
            },
            {
               "attribute" : "uro:RoadStructureAttribute_uro:width",
               "json_path" : "ancestors uro:RoadStructureAttribute uro:width",
               "data_type" : "real64"
            },
            {
               "attribute" : "uro:RoadStructureAttribute_uro:numberOfLanes",
               "json_path" : "ancestors uro:RoadStructureAttribute uro:numberOfLanes",
               "data_type" : "int16"
            },
            {
               "attribute" : "uro:RoadStructureAttribute_uro:sectionType",
               "json_path" : "ancestors uro:RoadStructureAttribute uro:sectionType",
               "data_type" : "buffer"
            },
            {
               "attribute" : "uro:TrafficVolumeAttribute_uro:sectionID",
               "json_path" : "ancestors uro:TrafficVolumeAttribute uro:sectionID",
               "data_type" : "buffer"
            },
            {
               "attribute" : "uro:TrafficVolumeAttribute_uro:routeName",
               "json_path" : "ancestors uro:TrafficVolumeAttribute uro:routeName",
               "data_type" : "buffer"
            },
            {
               "attribute" : "uro:TrafficVolumeAttribute_uro:weekday12hourTrafficVolume",
               "json_path" : "ancestors uro:TrafficVolumeAttribute uro:weekday12hourTrafficVolume",
               "data_type" : "real64"
            },
            {
               "attribute" : "uro:TrafficVolumeAttribute_uro:weekday24hourTrafficVolume",
               "json_path" : "ancestors uro:TrafficVolumeAttribute uro:weekday24hourTrafficVolume",
               "data_type" : "real64"
            },
            {
               "attribute" : "uro:TrafficVolumeAttribute_uro:largeVehicleRate",
               "json_path" : "ancestors uro:TrafficVolumeAttribute uro:largeVehicleRate",
               "data_type" : "real64"
            },
            {
               "attribute" : "uro:TrafficVolumeAttribute_uro:congestionRate",
               "json_path" : "ancestors uro:TrafficVolumeAttribute uro:congestionRate",
               "data_type" : "real64"
            },
            {
               "attribute" : "uro:TrafficVolumeAttribute_uro:averageTravelSpeedInCongestion",
               "json_path" : "ancestors uro:TrafficVolumeAttribute uro:averageTravelSpeedInCongestion",
               "data_type" : "real64"
            },
            {
               "attribute" : "uro:TrafficVolumeAttribute_uro:averageInboundTravelSpeedInCongestion",
               "json_path" : "ancestors uro:TrafficVolumeAttribute uro:averageInboundTravelSpeedInCongestion",
               "data_type" : "real64"
            },
            {
               "attribute" : "uro:TrafficVolumeAttribute_uro:averageOutboundTravelSpeedInCongestion",
               "json_path" : "ancestors uro:TrafficVolumeAttribute uro:averageOutboundTravelSpeedInCongestion",
               "data_type" : "real64"
            },
            {
               "attribute" : "uro:TrafficVolumeAttribute_uro:averageInboundTravelSpeedNotCongestion",
               "json_path" : "ancestors uro:TrafficVolumeAttribute uro:averageInboundTravelSpeedNotCongestion",
               "data_type" : "real64"
            },
            {
               "attribute" : "uro:TrafficVolumeAttribute_uro:averageOutboundTravelSpeedNotCongestion",
               "json_path" : "ancestors uro:TrafficVolumeAttribute uro:averageOutboundTravelSpeedNotCongestion",
               "data_type" : "real64"
            },
            {
               "attribute" : "uro:TrafficVolumeAttribute_uro:observationPointName",
               "json_path" : "ancestors uro:TrafficVolumeAttribute uro:observationPointName",
               "data_type" : "buffer"
            },
            {
               "attribute" : "uro:TrafficVolumeAttribute_uro:reference",
               "json_path" : "ancestors uro:TrafficVolumeAttribute uro:reference",
               "data_type" : "buffer"
            },
            {
               "attribute" : "uro:TrafficVolumeAttribute_uro:surveyYear",
               "json_path" : "ancestors uro:TrafficVolumeAttribute uro:surveyYear",
               "data_type" : "int16"
            },
            {
               "attribute" : "uro:geometrySrcDescLod1",
               "json_path" : "ancestors uro:DataQualityAttribute uro:geometrySrcDescLod1",
               "data_type" : "buffer"
            },
            {
               "attribute" : "uro:lodType",
               "json_path" : "ancestors uro:DataQualityAttribute uro:lodType",
               "data_type" : "buffer"
            }
         ],
         "tran/tran:AuxiliaryTrafficArea" : [
            {
               "attribute" : "gml:name",
               "json_path" : "ancestors gml:name",
               "data_type" : "buffer"
            },
            {
               "attribute" : "core:creationDate",
               "json_path" : "ancestors core:creationDate",
               "data_type" : "date"
            },
            {
               "attribute" : "tran:class",
               "json_path" : "ancestors tran:class",
               "data_type" : "buffer"
            },
            {
               "attribute" : "tran:Road_tran:function",
               "json_path" : "ancestors tran:function",
               "data_type" : "buffer"
            },
            {
               "attribute" : "tran:function",
               "json_path" : "tran:function",
               "data_type" : "buffer"
            },
            {
               "attribute" : "tran:surfaceMaterial",
               "json_path" : "tran:surfaceMaterial",
               "data_type" : "buffer"
            },
            {
               "attribute" : "tran:usage",
               "json_path" : "ancestors tran:usage",
               "data_type" : "buffer"
            },
            {
               "attribute" : "uro:RoadStructureAttribute_uro:widthType",
               "json_path" : "ancestors uro:RoadStructureAttribute uro:widthType",
               "data_type" : "buffer"
            },
            {
               "attribute" : "uro:RoadStructureAttribute_uro:width",
               "json_path" : "ancestors uro:RoadStructureAttribute uro:width",
               "data_type" : "real64"
            },
            {
               "attribute" : "uro:RoadStructureAttribute_uro:numberOfLanes",
               "json_path" : "ancestors uro:RoadStructureAttribute uro:numberOfLanes",
               "data_type" : "int16"
            },
            {
               "attribute" : "uro:RoadStructureAttribute_uro:sectionType",
               "json_path" : "ancestors uro:RoadStructureAttribute uro:sectionType",
               "data_type" : "buffer"
            },
            {
               "attribute" : "uro:TrafficVolumeAttribute_uro:sectionID",
               "json_path" : "ancestors uro:TrafficVolumeAttribute uro:sectionID",
               "data_type" : "buffer"
            },
            {
               "attribute" : "uro:TrafficVolumeAttribute_uro:routeName",
               "json_path" : "ancestors uro:TrafficVolumeAttribute uro:routeName",
               "data_type" : "buffer"
            },
            {
               "attribute" : "uro:TrafficVolumeAttribute_uro:weekday12hourTrafficVolume",
               "json_path" : "ancestors uro:TrafficVolumeAttribute uro:weekday12hourTrafficVolume",
               "data_type" : "real64"
            },
            {
               "attribute" : "uro:TrafficVolumeAttribute_uro:weekday24hourTrafficVolume",
               "json_path" : "ancestors uro:TrafficVolumeAttribute uro:weekday24hourTrafficVolume",
               "data_type" : "real64"
            },
            {
               "attribute" : "uro:TrafficVolumeAttribute_uro:largeVehicleRate",
               "json_path" : "ancestors uro:TrafficVolumeAttribute uro:largeVehicleRate",
               "data_type" : "real64"
            },
            {
               "attribute" : "uro:TrafficVolumeAttribute_uro:congestionRate",
               "json_path" : "ancestors uro:TrafficVolumeAttribute uro:congestionRate",
               "data_type" : "real64"
            },
            {
               "attribute" : "uro:TrafficVolumeAttribute_uro:averageTravelSpeedInCongestion",
               "json_path" : "ancestors uro:TrafficVolumeAttribute uro:averageTravelSpeedInCongestion",
               "data_type" : "real64"
            },
            {
               "attribute" : "uro:TrafficVolumeAttribute_uro:averageInboundTravelSpeedInCongestion",
               "json_path" : "ancestors uro:TrafficVolumeAttribute uro:averageInboundTravelSpeedInCongestion",
               "data_type" : "real64"
            },
            {
               "attribute" : "uro:TrafficVolumeAttribute_uro:averageOutboundTravelSpeedInCongestion",
               "json_path" : "ancestors uro:TrafficVolumeAttribute uro:averageOutboundTravelSpeedInCongestion",
               "data_type" : "real64"
            },
            {
               "attribute" : "uro:TrafficVolumeAttribute_uro:averageInboundTravelSpeedNotCongestion",
               "json_path" : "ancestors uro:TrafficVolumeAttribute uro:averageInboundTravelSpeedNotCongestion",
               "data_type" : "real64"
            },
            {
               "attribute" : "uro:TrafficVolumeAttribute_uro:averageOutboundTravelSpeedNotCongestion",
               "json_path" : "ancestors uro:TrafficVolumeAttribute uro:averageOutboundTravelSpeedNotCongestion",
               "data_type" : "real64"
            },
            {
               "attribute" : "uro:TrafficVolumeAttribute_uro:observationPointName",
               "json_path" : "ancestors uro:TrafficVolumeAttribute uro:observationPointName",
               "data_type" : "buffer"
            },
            {
               "attribute" : "uro:TrafficVolumeAttribute_uro:reference",
               "json_path" : "ancestors uro:TrafficVolumeAttribute uro:reference",
               "data_type" : "buffer"
            },
            {
               "attribute" : "uro:TrafficVolumeAttribute_uro:surveyYear",
               "json_path" : "ancestors uro:TrafficVolumeAttribute uro:surveyYear",
               "data_type" : "int16"
            },
            {
               "attribute" : "uro:geometrySrcDescLod1",
               "json_path" : "ancestors uro:DataQualityAttribute uro:geometrySrcDescLod1",
               "data_type" : "buffer"
            },
            {
               "attribute" : "uro:lodType",
               "json_path" : "ancestors uro:DataQualityAttribute uro:lodType",
               "data_type" : "buffer"
            }
         ],
         "rwy/tran:Railway" : [
            {
               "attribute" : "gml:name",
               "json_path" : "gml:name",
               "data_type" : "buffer"
            },
            {
               "attribute" : "core:creationDate",
               "json_path" : "core:creationDate",
               "data_type" : "date"
            },
            {
               "attribute" : "tran:class",
               "json_path" : "tran:class",
               "data_type" : "buffer"
            },
            {
               "attribute" : "tran:function",
               "json_path" : "tran:function",
               "data_type" : "buffer"
            },
            {
               "attribute" : "uro:operatorType",
               "json_path" : "uro:RailwayRouteAttribute uro:operatorType",
               "data_type" : "buffer"
            },
            {
               "attribute" : "uro:operator",
               "json_path" : "uro:RailwayRouteAttribute uro:operator",
               "data_type" : "buffer"
            },
            {
               "attribute" : "uro:railwayType",
               "json_path" : "uro:RailwayRouteAttribute uro:railwayType",
               "data_type" : "buffer"
            },
            {
               "attribute" : "uro:startStation",
               "json_path" : "uro:RailwayRouteAttribute uro:startStation",
               "data_type" : "buffer"
            },
            {
               "attribute" : "uro:endStation",
               "json_path" : "uro:RailwayRouteAttribute uro:endStation",
               "data_type" : "buffer"
            },
            {
               "attribute" : "uro:geometrySrcDescLod1",
               "json_path" : "uro:DataQualityAttribute uro:geometrySrcDescLod1",
               "data_type" : "buffer"
            },
            {
               "attribute" : "uro:lodType",
               "json_path" : "uro:DataQualityAttribute uro:lodType",
               "data_type" : "buffer"
            }
         ],
         "rwy/tran:TrafficArea" : [
            {
               "attribute" : "gml:name",
               "json_path" : "ancestors gml:name",
               "data_type" : "buffer"
            },
            {
               "attribute" : "core:creationDate",
               "json_path" : "ancestors core:creationDate",
               "data_type" : "date"
            },
            {
               "attribute" : "tran:class",
               "json_path" : "ancestors tran:class",
               "data_type" : "buffer"
            },
            {
               "attribute" : "tran:function",
               "json_path" : "ancestors tran:function",
               "data_type" : "buffer"
            },
            {
               "attribute" : "uro:operatorType",
               "json_path" : "ancestors uro:RailwayRouteAttribute uro:operatorType",
               "data_type" : "buffer"
            },
            {
               "attribute" : "uro:operator",
               "json_path" : "ancestors uro:RailwayRouteAttribute uro:operator",
               "data_type" : "buffer"
            },
            {
               "attribute" : "uro:railwayType",
               "json_path" : "ancestors uro:RailwayRouteAttribute uro:railwayType",
               "data_type" : "buffer"
            },
            {
               "attribute" : "uro:startStation",
               "json_path" : "ancestors uro:RailwayRouteAttribute uro:startStation",
               "data_type" : "buffer"
            },
            {
               "attribute" : "uro:endStation",
               "json_path" : "ancestors uro:RailwayRouteAttribute uro:endStation",
               "data_type" : "buffer"
            },
            {
               "attribute" : "uro:routeName",
               "json_path" : "uro:RailwayTrackAttribute uro:routeName",
               "data_type" : "buffer"
            },
            {
               "attribute" : "uro:directionType",
               "json_path" : "uro:RailwayTrackAttribute uro:directionType",
               "data_type" : "buffer"
            },
            {
               "attribute" : "uro:trackType",
               "json_path" : "uro:RailwayTrackAttribute uro:trackType",
               "data_type" : "buffer"
            },
            {
               "attribute" : "uro:startPost",
               "json_path" : "uro:RailwayTrackAttribute uro:startPost",
               "data_type" : "buffer"
            },
            {
               "attribute" : "uro:endPost",
               "json_path" : "uro:RailwayTrackAttribute uro:endPost",
               "data_type" : "buffer"
            },
            {
               "attribute" : "uro:alignmentType",
               "json_path" : "uro:RailwayTrackAttribute uro:alignmentType",
               "data_type" : "buffer"
            },
            {
               "attribute" : "uro:geometrySrcDescLod1",
               "json_path" : "ancestors uro:DataQualityAttribute uro:geometrySrcDescLod1",
               "data_type" : "buffer"
            },
            {
               "attribute" : "uro:lodType",
               "json_path" : "ancestors uro:DataQualityAttribute uro:lodType",
               "data_type" : "buffer"
            }
         ],
         "rwy/tran:AuxiliaryTrafficArea" : [
            {
               "attribute" : "gml:name",
               "json_path" : "ancestors gml:name",
               "data_type" : "buffer"
            },
            {
               "attribute" : "core:creationDate",
               "json_path" : "ancestors core:creationDate",
               "data_type" : "date"
            },
            {
               "attribute" : "tran:class",
               "json_path" : "ancestors tran:class",
               "data_type" : "buffer"
            },
            {
               "attribute" : "tran:function",
               "json_path" : "ancestors tran:function",
               "data_type" : "buffer"
            },
            {
               "attribute" : "uro:operatorType",
               "json_path" : "ancestors uro:RailwayRouteAttribute uro:operatorType",
               "data_type" : "buffer"
            },
            {
               "attribute" : "uro:operator",
               "json_path" : "ancestors uro:RailwayRouteAttribute uro:operator",
               "data_type" : "buffer"
            },
            {
               "attribute" : "uro:railwayType",
               "json_path" : "ancestors uro:RailwayRouteAttribute uro:railwayType",
               "data_type" : "buffer"
            },
            {
               "attribute" : "uro:startStation",
               "json_path" : "ancestors uro:RailwayRouteAttribute uro:startStation",
               "data_type" : "buffer"
            },
            {
               "attribute" : "uro:endStation",
               "json_path" : "ancestors uro:RailwayRouteAttribute uro:endStation",
               "data_type" : "buffer"
            },
            {
               "attribute" : "uro:geometrySrcDescLod1",
               "json_path" : "ancestors uro:DataQualityAttribute uro:geometrySrcDescLod1",
               "data_type" : "buffer"
            },
            {
               "attribute" : "uro:lodType",
               "json_path" : "ancestors uro:DataQualityAttribute uro:lodType",
               "data_type" : "buffer"
            }
         ],
         "trk/tran:Track" : [
            {
               "attribute" : "gml:name",
               "json_path" : "gml:name",
               "data_type" : "buffer"
            },
            {
               "attribute" : "core:creationDate",
               "json_path" : "core:creationDate",
               "data_type" : "date"
            },
            {
               "attribute" : "tran:class",
               "json_path" : "tran:class",
               "data_type" : "buffer"
            },
            {
               "attribute" : "tran:function",
               "json_path" : "tran:function",
               "data_type" : "buffer"
            },
            {
               "attribute" : "tran:usage",
               "json_path" : "tran:usage",
               "data_type" : "buffer"
            },
            {
               "attribute" : "uro:geometrySrcDescLod1",
               "json_path" : "uro:DataQualityAttribute uro:geometrySrcDescLod1",
               "data_type" : "buffer"
            },
            {
               "attribute" : "uro:lodType",
               "json_path" : "uro:DataQualityAttribute uro:lodType",
               "data_type" : "buffer"
            }
         ],
         "trk/tran:TrafficArea" : [
            {
               "attribute" : "gml:name",
               "json_path" : "ancestors gml:name",
               "data_type" : "buffer"
            },
            {
               "attribute" : "core:creationDate",
               "json_path" : "ancestors core:creationDate",
               "data_type" : "date"
            },
            {
               "attribute" : "tran:class",
               "json_path" : "ancestors tran:class",
               "data_type" : "buffer"
            },
            {
               "attribute" : "tran:Track_tran:function",
               "json_path" : "ancestors tran:function",
               "data_type" : "buffer"
            },
            {
               "attribute" : "tran:function",
               "json_path" : "tran:function",
               "data_type" : "buffer"
            },
            {
               "attribute" : "tran:usage",
               "json_path" : "ancestors tran:usage",
               "data_type" : "buffer"
            },
            {
               "attribute" : "uro:geometrySrcDescLod1",
               "json_path" : "ancestors uro:DataQualityAttribute uro:geometrySrcDescLod1",
               "data_type" : "buffer"
            },
            {
               "attribute" : "uro:lodType",
               "json_path" : "ancestors uro:DataQualityAttribute uro:lodType",
               "data_type" : "buffer"
            }
         ],
         "trk/tran:AuxiliaryTrafficArea" : [
            {
               "attribute" : "gml:name",
               "json_path" : "ancestors gml:name",
               "data_type" : "buffer"
            },
            {
               "attribute" : "core:creationDate",
               "json_path" : "ancestors core:creationDate",
               "data_type" : "date"
            },
            {
               "attribute" : "tran:class",
               "json_path" : "ancestors tran:class",
               "data_type" : "buffer"
            },
            {
               "attribute" : "tran:Track_tran:function",
               "json_path" : "ancestors tran:function",
               "data_type" : "buffer"
            },
            {
               "attribute" : "tran:function",
               "json_path" : "tran:function",
               "data_type" : "buffer"
            },
            {
               "attribute" : "tran:usage",
               "json_path" : "ancestors tran:usage",
               "data_type" : "buffer"
            },
            {
               "attribute" : "uro:geometrySrcDescLod1",
               "json_path" : "ancestors uro:DataQualityAttribute uro:geometrySrcDescLod1",
               "data_type" : "buffer"
            },
            {
               "attribute" : "uro:lodType",
               "json_path" : "ancestors uro:DataQualityAttribute uro:lodType",
               "data_type" : "buffer"
            }
         ],
         "squr/tran:Square" : [
            {
               "attribute" : "gml:name",
               "json_path" : "gml:name",
               "data_type" : "buffer"
            },
            {
               "attribute" : "core:creationDate",
               "json_path" : "core:creationDate",
               "data_type" : "date"
            },
            {
               "attribute" : "tran:class",
               "json_path" : "tran:class",
               "data_type" : "buffer"
            },
            {
               "attribute" : "tran:function",
               "json_path" : "tran:function",
               "data_type" : "buffer"
            },
            {
               "attribute" : "uro:SquareUrbanPlanAttribute_uro:prefecture",
               "json_path" : "uro:SquareUrbanPlanAttribute uro:prefecture",
               "data_type" : "buffer"
            },
            {
               "attribute" : "uro:SquareUrbanPlanAttribute_uro:city",
               "json_path" : "uro:SquareUrbanPlanAttribute uro:city",
               "data_type" : "buffer"
            },
            {
               "attribute" : "uro:SquareUrbanPlanAttribute_uro:urbanPlanningAreaName",
               "json_path" : "uro:SquareUrbanPlanAttribute uro:urbanPlanningAreaName",
               "data_type" : "buffer"
            },
            {
               "attribute" : "uro:SquareUrbanPlanAttribute_uro:enforcer",
               "json_path" : "uro:SquareUrbanPlanAttribute uro:enforcer",
               "data_type" : "buffer"
            },
            {
               "attribute" : "uro:SquareUrbanPlanAttribute_uro:dateOfDecision",
               "json_path" : "uro:SquareUrbanPlanAttribute uro:dateOfDecision",
               "data_type" : "date"
            },
            {
               "attribute" : "uro:SquareUrbanPlanAttribute_uro:dateOfRevision",
               "json_path" : "uro:SquareUrbanPlanAttribute uro:dateOfRevision",
               "data_type" : "date"
            },
            {
               "attribute" : "uro:SquareUrbanPlanAttribute_uro:areaPlanned",
               "json_path" : "uro:SquareUrbanPlanAttribute uro:areaPlanned",
               "data_type" : "real64"
            },
            {
               "attribute" : "uro:SquareUrbanPlanAttribute_uro:areaInService",
               "json_path" : "uro:SquareUrbanPlanAttribute uro:areaInService",
               "data_type" : "real64"
            },
            {
               "attribute" : "uro:SquareUrbanPlanAttribute_uro:remarks",
               "json_path" : "uro:SquareUrbanPlanAttribute uro:remarks",
               "data_type" : "buffer"
            },
            {
               "attribute" : "uro:SquareUrbanPlanAttribute_uro:status",
               "json_path" : "uro:SquareUrbanPlanAttribute uro:status",
               "data_type" : "buffer"
            },
            {
               "attribute" : "uro:SquareUrbanPlanAttribute_uro:areaImproved",
               "json_path" : "uro:SquareUrbanPlanAttribute uro:areaImproved",
               "data_type" : "real64"
            },
            {
               "attribute" : "uro:SquareUrbanPlanAttribute_uro:areaCompleted",
               "json_path" : "uro:SquareUrbanPlanAttribute uro:areaCompleted",
               "data_type" : "real64"
            },
            {
               "attribute" : "uro:SquareUrbanPlanAttribute_uro:projectStartDate",
               "json_path" : "uro:SquareUrbanPlanAttribute uro:projectStartDate",
               "data_type" : "date"
            },
            {
               "attribute" : "uro:SquareUrbanPlanAttribute_uro:projectEndDate",
               "json_path" : "uro:SquareUrbanPlanAttribute uro:projectEndDate",
               "data_type" : "date"
            },
            {
               "attribute" : "uro:SquareUrbanPlanAttribute_uro:isCompleted",
               "json_path" : "uro:SquareUrbanPlanAttribute uro:isCompleted",
               "data_type" : "buffer"
            },
            {
               "attribute" : "uro:SquareUrbanPlanAttribute_uro:isAuthorized",
               "json_path" : "uro:SquareUrbanPlanAttribute uro:isAuthorized",
               "data_type" : "buffer"
            },
            {
               "attribute" : "uro:SquareUrbanPlanAttribute_uro:purpose",
               "json_path" : "uro:SquareUrbanPlanAttribute uro:purpose",
               "data_type" : "buffer"
            },
            {
               "attribute" : "uro:SquareUrbanPlanAttribute_uro:note",
               "json_path" : "uro:SquareUrbanPlanAttribute uro:note",
               "data_type" : "buffer"
            },
            {
               "attribute" : "uro:StationSquareAttribute_uro:prefecture",
               "json_path" : "uro:StationSquareAttribute uro:prefecture",
               "data_type" : "buffer"
            },
            {
               "attribute" : "uro:StationSquareAttribute_uro:city",
               "json_path" : "uro:StationSquareAttribute uro:city",
               "data_type" : "buffer"
            },
            {
               "attribute" : "uro:StationSquareAttribute_uro:urbanPlanningAreaName",
               "json_path" : "uro:StationSquareAttribute uro:urbanPlanningAreaName",
               "data_type" : "buffer"
            },
            {
               "attribute" : "uro:StationSquareAttribute_uro:enforcer",
               "json_path" : "uro:StationSquareAttribute uro:enforcer",
               "data_type" : "buffer"
            },
            {
               "attribute" : "uro:StationSquareAttribute_uro:dateOfDecision",
               "json_path" : "uro:StationSquareAttribute uro:dateOfDecision",
               "data_type" : "date"
            },
            {
               "attribute" : "uro:StationSquareAttribute_uro:dateOfRevision",
               "json_path" : "uro:StationSquareAttribute uro:dateOfRevision",
               "data_type" : "date"
            },
            {
               "attribute" : "uro:StationSquareAttribute_uro:areaPlanned",
               "json_path" : "uro:StationSquareAttribute uro:areaPlanned",
               "data_type" : "real64"
            },
            {
               "attribute" : "uro:StationSquareAttribute_uro:areaInService",
               "json_path" : "uro:StationSquareAttribute uro:areaInService",
               "data_type" : "real64"
            },
            {
               "attribute" : "uro:StationSquareAttribute_uro:remarks",
               "json_path" : "uro:StationSquareAttribute uro:remarks",
               "data_type" : "buffer"
            },
            {
               "attribute" : "uro:StationSquareAttribute_uro:status",
               "json_path" : "uro:StationSquareAttribute uro:status",
               "data_type" : "buffer"
            },
            {
               "attribute" : "uro:StationSquareAttribute_uro:areaImproved",
               "json_path" : "uro:StationSquareAttribute uro:areaImproved",
               "data_type" : "real64"
            },
            {
               "attribute" : "uro:StationSquareAttribute_uro:areaCompleted",
               "json_path" : "uro:StationSquareAttribute uro:areaCompleted",
               "data_type" : "real64"
            },
            {
               "attribute" : "uro:StationSquareAttribute_uro:projectStartDate",
               "json_path" : "uro:StationSquareAttribute uro:projectStartDate",
               "data_type" : "date"
            },
            {
               "attribute" : "uro:StationSquareAttribute_uro:projectEndDate",
               "json_path" : "uro:StationSquareAttribute uro:projectEndDate",
               "data_type" : "date"
            },
            {
               "attribute" : "uro:StationSquareAttribute_uro:isCompleted",
               "json_path" : "uro:StationSquareAttribute uro:isCompleted",
               "data_type" : "buffer"
            },
            {
               "attribute" : "uro:StationSquareAttribute_uro:isAuthorized",
               "json_path" : "uro:StationSquareAttribute uro:isAuthorized",
               "data_type" : "buffer"
            },
            {
               "attribute" : "uro:StationSquareAttribute_uro:purpose",
               "json_path" : "uro:StationSquareAttribute uro:purpose",
               "data_type" : "buffer"
            },
            {
               "attribute" : "uro:StationSquareAttribute_uro:note",
               "json_path" : "uro:StationSquareAttribute uro:note",
               "data_type" : "buffer"
            },
            {
               "attribute" : "uro:StationSquareAttribute_uro:station",
               "json_path" : "uro:StationSquareAttribute uro:station",
               "data_type" : "buffer"
            },
            {
               "attribute" : "uro:StationSquareAttribute_uro:route",
               "json_path" : "uro:StationSquareAttribute uro:route",
               "data_type" : "buffer"
            },
            {
               "attribute" : "uro:StationSquareAttribute_uro:railwayType",
               "json_path" : "uro:StationSquareAttribute uro:railwayType",
               "data_type" : "buffer"
            },
            {
               "attribute" : "uro:TerminalAttribute_uro:prefecture",
               "json_path" : "uro:TerminalAttribute uro:prefecture",
               "data_type" : "buffer"
            },
            {
               "attribute" : "uro:TerminalAttribute_uro:city",
               "json_path" : "uro:TerminalAttribute uro:city",
               "data_type" : "buffer"
            },
            {
               "attribute" : "uro:TerminalAttribute_uro:urbanPlanningAreaName",
               "json_path" : "uro:TerminalAttribute uro:urbanPlanningAreaName",
               "data_type" : "buffer"
            },
            {
               "attribute" : "uro:TerminalAttribute_uro:enforcer",
               "json_path" : "uro:TerminalAttribute uro:enforcer",
               "data_type" : "buffer"
            },
            {
               "attribute" : "uro:TerminalAttribute_uro:dateOfDecision",
               "json_path" : "uro:TerminalAttribute uro:dateOfDecision",
               "data_type" : "date"
            },
            {
               "attribute" : "uro:TerminalAttribute_uro:dateOfRevision",
               "json_path" : "uro:TerminalAttribute uro:dateOfRevision",
               "data_type" : "date"
            },
            {
               "attribute" : "uro:TerminalAttribute_uro:areaPlanned",
               "json_path" : "uro:TerminalAttribute uro:areaPlanned",
               "data_type" : "real64"
            },
            {
               "attribute" : "uro:TerminalAttribute_uro:areaInService",
               "json_path" : "uro:TerminalAttribute uro:areaInService",
               "data_type" : "real64"
            },
            {
               "attribute" : "uro:TerminalAttribute_uro:remarks",
               "json_path" : "uro:TerminalAttribute uro:remarks",
               "data_type" : "buffer"
            },
            {
               "attribute" : "uro:TerminalAttribute_uro:status",
               "json_path" : "uro:TerminalAttribute uro:status",
               "data_type" : "buffer"
            },
            {
               "attribute" : "uro:TerminalAttribute_uro:areaImproved",
               "json_path" : "uro:TerminalAttribute uro:areaImproved",
               "data_type" : "real64"
            },
            {
               "attribute" : "uro:TerminalAttribute_uro:areaCompleted",
               "json_path" : "uro:TerminalAttribute uro:areaCompleted",
               "data_type" : "real64"
            },
            {
               "attribute" : "uro:TerminalAttribute_uro:projectStartDate",
               "json_path" : "uro:TerminalAttribute uro:projectStartDate",
               "data_type" : "date"
            },
            {
               "attribute" : "uro:TerminalAttribute_uro:projectEndDate",
               "json_path" : "uro:TerminalAttribute uro:projectEndDate",
               "data_type" : "date"
            },
            {
               "attribute" : "uro:TerminalAttribute_uro:isCompleted",
               "json_path" : "uro:TerminalAttribute uro:isCompleted",
               "data_type" : "buffer"
            },
            {
               "attribute" : "uro:TerminalAttribute_uro:isAuthorized",
               "json_path" : "uro:TerminalAttribute uro:isAuthorized",
               "data_type" : "buffer"
            },
            {
               "attribute" : "uro:TerminalAttribute_uro:purpose",
               "json_path" : "uro:TerminalAttribute uro:purpose",
               "data_type" : "buffer"
            },
            {
               "attribute" : "uro:TerminalAttribute_uro:note",
               "json_path" : "uro:TerminalAttribute uro:note",
               "data_type" : "buffer"
            },
            {
               "attribute" : "uro:TerminalAttribute_uro:terminalType",
               "json_path" : "uro:TerminalAttribute uro:terminalType",
               "data_type" : "buffer"
            },
            {
               "attribute" : "uro:TerminalAttribute_uro:structure",
               "json_path" : "uro:TerminalAttribute uro:structure",
               "data_type" : "buffer"
            },
            {
               "attribute" : "uro:TerminalAttribute_uro:numberOfBerthsPlanned",
               "json_path" : "uro:TerminalAttribute uro:numberOfBerthsPlanned",
               "data_type" : "int16"
            },
            {
               "attribute" : "uro:TerminalAttribute_uro:numberOfBerthsInService",
               "json_path" : "uro:TerminalAttribute uro:numberOfBerthsInService",
               "data_type" : "int16"
            },
            {
               "attribute" : "uro:TerminalAttribute_uro:userType",
               "json_path" : "uro:TerminalAttribute uro:userType",
               "data_type" : "buffer"
            },
            {
               "attribute" : "uro:geometrySrcDescLod1",
               "json_path" : "uro:DataQualityAttribute uro:geometrySrcDescLod1",
               "data_type" : "buffer"
            },
            {
               "attribute" : "uro:lodType",
               "json_path" : "uro:DataQualityAttribute uro:lodType",
               "data_type" : "buffer"
            }
         ],
         "squr/tran:TrafficArea" : [
            {
               "attribute" : "gml:name",
               "json_path" : "ancestors gml:name",
               "data_type" : "buffer"
            },
            {
               "attribute" : "core:creationDate",
               "json_path" : "ancestors core:creationDate",
               "data_type" : "date"
            },
            {
               "attribute" : "tran:class",
               "json_path" : "ancestors tran:class",
               "data_type" : "buffer"
            },
            {
               "attribute" : "tran:Square_tran:function",
               "json_path" : "ancestors tran:function",
               "data_type" : "buffer"
            },
            {
               "attribute" : "tran:function",
               "json_path" : "tran:function",
               "data_type" : "buffer"
            },
            {
               "attribute" : "uro:SquareUrbanPlanAttribute_uro:prefecture",
               "json_path" : "ancestors uro:SquareUrbanPlanAttribute uro:prefecture",
               "data_type" : "buffer"
            },
            {
               "attribute" : "uro:SquareUrbanPlanAttribute_uro:city",
               "json_path" : "ancestors uro:SquareUrbanPlanAttribute uro:city",
               "data_type" : "buffer"
            },
            {
               "attribute" : "uro:SquareUrbanPlanAttribute_uro:urbanPlanningAreaName",
               "json_path" : "ancestors uro:SquareUrbanPlanAttribute uro:urbanPlanningAreaName",
               "data_type" : "buffer"
            },
            {
               "attribute" : "uro:SquareUrbanPlanAttribute_uro:enforcer",
               "json_path" : "ancestors uro:SquareUrbanPlanAttribute uro:enforcer",
               "data_type" : "buffer"
            },
            {
               "attribute" : "uro:SquareUrbanPlanAttribute_uro:dateOfDecision",
               "json_path" : "ancestors uro:SquareUrbanPlanAttribute uro:dateOfDecision",
               "data_type" : "date"
            },
            {
               "attribute" : "uro:SquareUrbanPlanAttribute_uro:dateOfRevision",
               "json_path" : "ancestors uro:SquareUrbanPlanAttribute uro:dateOfRevision",
               "data_type" : "date"
            },
            {
               "attribute" : "uro:SquareUrbanPlanAttribute_uro:areaPlanned",
               "json_path" : "ancestors uro:SquareUrbanPlanAttribute uro:areaPlanned",
               "data_type" : "real64"
            },
            {
               "attribute" : "uro:SquareUrbanPlanAttribute_uro:areaInService",
               "json_path" : "ancestors uro:SquareUrbanPlanAttribute uro:areaInService",
               "data_type" : "real64"
            },
            {
               "attribute" : "uro:SquareUrbanPlanAttribute_uro:remarks",
               "json_path" : "ancestors uro:SquareUrbanPlanAttribute uro:remarks",
               "data_type" : "buffer"
            },
            {
               "attribute" : "uro:SquareUrbanPlanAttribute_uro:status",
               "json_path" : "ancestors uro:SquareUrbanPlanAttribute uro:status",
               "data_type" : "buffer"
            },
            {
               "attribute" : "uro:SquareUrbanPlanAttribute_uro:areaImproved",
               "json_path" : "ancestors uro:SquareUrbanPlanAttribute uro:areaImproved",
               "data_type" : "real64"
            },
            {
               "attribute" : "uro:SquareUrbanPlanAttribute_uro:areaCompleted",
               "json_path" : "ancestors uro:SquareUrbanPlanAttribute uro:areaCompleted",
               "data_type" : "real64"
            },
            {
               "attribute" : "uro:SquareUrbanPlanAttribute_uro:projectStartDate",
               "json_path" : "ancestors uro:SquareUrbanPlanAttribute uro:projectStartDate",
               "data_type" : "date"
            },
            {
               "attribute" : "uro:SquareUrbanPlanAttribute_uro:projectEndDate",
               "json_path" : "ancestors uro:SquareUrbanPlanAttribute uro:projectEndDate",
               "data_type" : "date"
            },
            {
               "attribute" : "uro:SquareUrbanPlanAttribute_uro:isCompleted",
               "json_path" : "ancestors uro:SquareUrbanPlanAttribute uro:isCompleted",
               "data_type" : "buffer"
            },
            {
               "attribute" : "uro:SquareUrbanPlanAttribute_uro:isAuthorized",
               "json_path" : "ancestors uro:SquareUrbanPlanAttribute uro:isAuthorized",
               "data_type" : "buffer"
            },
            {
               "attribute" : "uro:SquareUrbanPlanAttribute_uro:purpose",
               "json_path" : "ancestors uro:SquareUrbanPlanAttribute uro:purpose",
               "data_type" : "buffer"
            },
            {
               "attribute" : "uro:SquareUrbanPlanAttribute_uro:note",
               "json_path" : "ancestors uro:SquareUrbanPlanAttribute uro:note",
               "data_type" : "buffer"
            },
            {
               "attribute" : "uro:StationSquareAttribute_uro:prefecture",
               "json_path" : "ancestors uro:StationSquareAttribute uro:prefecture",
               "data_type" : "buffer"
            },
            {
               "attribute" : "uro:StationSquareAttribute_uro:city",
               "json_path" : "ancestors uro:StationSquareAttribute uro:city",
               "data_type" : "buffer"
            },
            {
               "attribute" : "uro:StationSquareAttribute_uro:urbanPlanningAreaName",
               "json_path" : "ancestors uro:StationSquareAttribute uro:urbanPlanningAreaName",
               "data_type" : "buffer"
            },
            {
               "attribute" : "uro:StationSquareAttribute_uro:enforcer",
               "json_path" : "ancestors uro:StationSquareAttribute uro:enforcer",
               "data_type" : "buffer"
            },
            {
               "attribute" : "uro:StationSquareAttribute_uro:dateOfDecision",
               "json_path" : "ancestors uro:StationSquareAttribute uro:dateOfDecision",
               "data_type" : "date"
            },
            {
               "attribute" : "uro:StationSquareAttribute_uro:dateOfRevision",
               "json_path" : "ancestors uro:StationSquareAttribute uro:dateOfRevision",
               "data_type" : "date"
            },
            {
               "attribute" : "uro:StationSquareAttribute_uro:areaPlanned",
               "json_path" : "ancestors uro:StationSquareAttribute uro:areaPlanned",
               "data_type" : "real64"
            },
            {
               "attribute" : "uro:StationSquareAttribute_uro:areaInService",
               "json_path" : "ancestors uro:StationSquareAttribute uro:areaInService",
               "data_type" : "real64"
            },
            {
               "attribute" : "uro:StationSquareAttribute_uro:remarks",
               "json_path" : "ancestors uro:StationSquareAttribute uro:remarks",
               "data_type" : "buffer"
            },
            {
               "attribute" : "uro:StationSquareAttribute_uro:status",
               "json_path" : "ancestors uro:StationSquareAttribute uro:status",
               "data_type" : "buffer"
            },
            {
               "attribute" : "uro:StationSquareAttribute_uro:areaImproved",
               "json_path" : "ancestors uro:StationSquareAttribute uro:areaImproved",
               "data_type" : "real64"
            },
            {
               "attribute" : "uro:StationSquareAttribute_uro:areaCompleted",
               "json_path" : "ancestors uro:StationSquareAttribute uro:areaCompleted",
               "data_type" : "real64"
            },
            {
               "attribute" : "uro:StationSquareAttribute_uro:projectStartDate",
               "json_path" : "ancestors uro:StationSquareAttribute uro:projectStartDate",
               "data_type" : "date"
            },
            {
               "attribute" : "uro:StationSquareAttribute_uro:projectEndDate",
               "json_path" : "ancestors uro:StationSquareAttribute uro:projectEndDate",
               "data_type" : "date"
            },
            {
               "attribute" : "uro:StationSquareAttribute_uro:isCompleted",
               "json_path" : "ancestors uro:StationSquareAttribute uro:isCompleted",
               "data_type" : "buffer"
            },
            {
               "attribute" : "uro:StationSquareAttribute_uro:isAuthorized",
               "json_path" : "ancestors uro:StationSquareAttribute uro:isAuthorized",
               "data_type" : "buffer"
            },
            {
               "attribute" : "uro:StationSquareAttribute_uro:purpose",
               "json_path" : "ancestors uro:StationSquareAttribute uro:purpose",
               "data_type" : "buffer"
            },
            {
               "attribute" : "uro:StationSquareAttribute_uro:note",
               "json_path" : "ancestors uro:StationSquareAttribute uro:note",
               "data_type" : "buffer"
            },
            {
               "attribute" : "uro:StationSquareAttribute_uro:station",
               "json_path" : "ancestors uro:StationSquareAttribute uro:station",
               "data_type" : "buffer"
            },
            {
               "attribute" : "uro:StationSquareAttribute_uro:route",
               "json_path" : "ancestors uro:StationSquareAttribute uro:route",
               "data_type" : "buffer"
            },
            {
               "attribute" : "uro:StationSquareAttribute_uro:railwayType",
               "json_path" : "ancestors uro:StationSquareAttribute uro:railwayType",
               "data_type" : "buffer"
            },
            {
               "attribute" : "uro:TerminalAttribute_uro:prefecture",
               "json_path" : "ancestors uro:TerminalAttribute uro:prefecture",
               "data_type" : "buffer"
            },
            {
               "attribute" : "uro:TerminalAttribute_uro:city",
               "json_path" : "ancestors uro:TerminalAttribute uro:city",
               "data_type" : "buffer"
            },
            {
               "attribute" : "uro:TerminalAttribute_uro:urbanPlanningAreaName",
               "json_path" : "ancestors uro:TerminalAttribute uro:urbanPlanningAreaName",
               "data_type" : "buffer"
            },
            {
               "attribute" : "uro:TerminalAttribute_uro:enforcer",
               "json_path" : "ancestors uro:TerminalAttribute uro:enforcer",
               "data_type" : "buffer"
            },
            {
               "attribute" : "uro:TerminalAttribute_uro:dateOfDecision",
               "json_path" : "ancestors uro:TerminalAttribute uro:dateOfDecision",
               "data_type" : "date"
            },
            {
               "attribute" : "uro:TerminalAttribute_uro:dateOfRevision",
               "json_path" : "ancestors uro:TerminalAttribute uro:dateOfRevision",
               "data_type" : "date"
            },
            {
               "attribute" : "uro:TerminalAttribute_uro:areaPlanned",
               "json_path" : "ancestors uro:TerminalAttribute uro:areaPlanned",
               "data_type" : "real64"
            },
            {
               "attribute" : "uro:TerminalAttribute_uro:areaInService",
               "json_path" : "ancestors uro:TerminalAttribute uro:areaInService",
               "data_type" : "real64"
            },
            {
               "attribute" : "uro:TerminalAttribute_uro:remarks",
               "json_path" : "ancestors uro:TerminalAttribute uro:remarks",
               "data_type" : "buffer"
            },
            {
               "attribute" : "uro:TerminalAttribute_uro:status",
               "json_path" : "ancestors uro:TerminalAttribute uro:status",
               "data_type" : "buffer"
            },
            {
               "attribute" : "uro:TerminalAttribute_uro:areaImproved",
               "json_path" : "ancestors uro:TerminalAttribute uro:areaImproved",
               "data_type" : "real64"
            },
            {
               "attribute" : "uro:TerminalAttribute_uro:areaCompleted",
               "json_path" : "ancestors uro:TerminalAttribute uro:areaCompleted",
               "data_type" : "real64"
            },
            {
               "attribute" : "uro:TerminalAttribute_uro:projectStartDate",
               "json_path" : "ancestors uro:TerminalAttribute uro:projectStartDate",
               "data_type" : "date"
            },
            {
               "attribute" : "uro:TerminalAttribute_uro:projectEndDate",
               "json_path" : "ancestors uro:TerminalAttribute uro:projectEndDate",
               "data_type" : "date"
            },
            {
               "attribute" : "uro:TerminalAttribute_uro:isCompleted",
               "json_path" : "ancestors uro:TerminalAttribute uro:isCompleted",
               "data_type" : "buffer"
            },
            {
               "attribute" : "uro:TerminalAttribute_uro:isAuthorized",
               "json_path" : "ancestors uro:TerminalAttribute uro:isAuthorized",
               "data_type" : "buffer"
            },
            {
               "attribute" : "uro:TerminalAttribute_uro:purpose",
               "json_path" : "ancestors uro:TerminalAttribute uro:purpose",
               "data_type" : "buffer"
            },
            {
               "attribute" : "uro:TerminalAttribute_uro:note",
               "json_path" : "ancestors uro:TerminalAttribute uro:note",
               "data_type" : "buffer"
            },
            {
               "attribute" : "uro:TerminalAttribute_uro:terminalType",
               "json_path" : "ancestors uro:TerminalAttribute uro:terminalType",
               "data_type" : "buffer"
            },
            {
               "attribute" : "uro:TerminalAttribute_uro:structure",
               "json_path" : "ancestors uro:TerminalAttribute uro:structure",
               "data_type" : "buffer"
            },
            {
               "attribute" : "uro:TerminalAttribute_uro:numberOfBerthsPlanned",
               "json_path" : "ancestors uro:TerminalAttribute uro:numberOfBerthsPlanned",
               "data_type" : "int16"
            },
            {
               "attribute" : "uro:TerminalAttribute_uro:numberOfBerthsInService",
               "json_path" : "ancestors uro:TerminalAttribute uro:numberOfBerthsInService",
               "data_type" : "int16"
            },
            {
               "attribute" : "uro:TerminalAttribute_uro:userType",
               "json_path" : "ancestors uro:TerminalAttribute uro:userType",
               "data_type" : "buffer"
            },
            {
               "attribute" : "uro:geometrySrcDescLod1",
               "json_path" : "ancestors uro:DataQualityAttribute uro:geometrySrcDescLod1",
               "data_type" : "buffer"
            },
            {
               "attribute" : "uro:lodType",
               "json_path" : "ancestors uro:DataQualityAttribute uro:lodType",
               "data_type" : "buffer"
            }
         ],
         "squr/tran:AuxiliaryTrafficArea" : [
            {
               "attribute" : "gml:name",
               "json_path" : "ancestors gml:name",
               "data_type" : "buffer"
            },
            {
               "attribute" : "core:creationDate",
               "json_path" : "ancestors core:creationDate",
               "data_type" : "date"
            },
            {
               "attribute" : "tran:class",
               "json_path" : "ancestors tran:class",
               "data_type" : "buffer"
            },
            {
               "attribute" : "tran:Square_tran:function",
               "json_path" : "ancestors tran:function",
               "data_type" : "buffer"
            },
            {
               "attribute" : "tran:function",
               "json_path" : "tran:function",
               "data_type" : "buffer"
            },
            {
               "attribute" : "uro:SquareUrbanPlanAttribute_uro:prefecture",
               "json_path" : "ancestors uro:SquareUrbanPlanAttribute uro:prefecture",
               "data_type" : "buffer"
            },
            {
               "attribute" : "uro:SquareUrbanPlanAttribute_uro:city",
               "json_path" : "ancestors uro:SquareUrbanPlanAttribute uro:city",
               "data_type" : "buffer"
            },
            {
               "attribute" : "uro:SquareUrbanPlanAttribute_uro:urbanPlanningAreaName",
               "json_path" : "ancestors uro:SquareUrbanPlanAttribute uro:urbanPlanningAreaName",
               "data_type" : "buffer"
            },
            {
               "attribute" : "uro:SquareUrbanPlanAttribute_uro:enforcer",
               "json_path" : "ancestors uro:SquareUrbanPlanAttribute uro:enforcer",
               "data_type" : "buffer"
            },
            {
               "attribute" : "uro:SquareUrbanPlanAttribute_uro:dateOfDecision",
               "json_path" : "ancestors uro:SquareUrbanPlanAttribute uro:dateOfDecision",
               "data_type" : "date"
            },
            {
               "attribute" : "uro:SquareUrbanPlanAttribute_uro:dateOfRevision",
               "json_path" : "ancestors uro:SquareUrbanPlanAttribute uro:dateOfRevision",
               "data_type" : "date"
            },
            {
               "attribute" : "uro:SquareUrbanPlanAttribute_uro:areaPlanned",
               "json_path" : "ancestors uro:SquareUrbanPlanAttribute uro:areaPlanned",
               "data_type" : "real64"
            },
            {
               "attribute" : "uro:SquareUrbanPlanAttribute_uro:areaInService",
               "json_path" : "ancestors uro:SquareUrbanPlanAttribute uro:areaInService",
               "data_type" : "real64"
            },
            {
               "attribute" : "uro:SquareUrbanPlanAttribute_uro:remarks",
               "json_path" : "ancestors uro:SquareUrbanPlanAttribute uro:remarks",
               "data_type" : "buffer"
            },
            {
               "attribute" : "uro:SquareUrbanPlanAttribute_uro:status",
               "json_path" : "ancestors uro:SquareUrbanPlanAttribute uro:status",
               "data_type" : "buffer"
            },
            {
               "attribute" : "uro:SquareUrbanPlanAttribute_uro:areaImproved",
               "json_path" : "ancestors uro:SquareUrbanPlanAttribute uro:areaImproved",
               "data_type" : "real64"
            },
            {
               "attribute" : "uro:SquareUrbanPlanAttribute_uro:areaCompleted",
               "json_path" : "ancestors uro:SquareUrbanPlanAttribute uro:areaCompleted",
               "data_type" : "real64"
            },
            {
               "attribute" : "uro:SquareUrbanPlanAttribute_uro:projectStartDate",
               "json_path" : "ancestors uro:SquareUrbanPlanAttribute uro:projectStartDate",
               "data_type" : "date"
            },
            {
               "attribute" : "uro:SquareUrbanPlanAttribute_uro:projectEndDate",
               "json_path" : "ancestors uro:SquareUrbanPlanAttribute uro:projectEndDate",
               "data_type" : "date"
            },
            {
               "attribute" : "uro:SquareUrbanPlanAttribute_uro:isCompleted",
               "json_path" : "ancestors uro:SquareUrbanPlanAttribute uro:isCompleted",
               "data_type" : "buffer"
            },
            {
               "attribute" : "uro:SquareUrbanPlanAttribute_uro:isAuthorized",
               "json_path" : "ancestors uro:SquareUrbanPlanAttribute uro:isAuthorized",
               "data_type" : "buffer"
            },
            {
               "attribute" : "uro:SquareUrbanPlanAttribute_uro:purpose",
               "json_path" : "ancestors uro:SquareUrbanPlanAttribute uro:purpose",
               "data_type" : "buffer"
            },
            {
               "attribute" : "uro:SquareUrbanPlanAttribute_uro:note",
               "json_path" : "ancestors uro:SquareUrbanPlanAttribute uro:note",
               "data_type" : "buffer"
            },
            {
               "attribute" : "uro:StationSquareAttribute_uro:prefecture",
               "json_path" : "ancestors uro:StationSquareAttribute uro:prefecture",
               "data_type" : "buffer"
            },
            {
               "attribute" : "uro:StationSquareAttribute_uro:city",
               "json_path" : "ancestors uro:StationSquareAttribute uro:city",
               "data_type" : "buffer"
            },
            {
               "attribute" : "uro:StationSquareAttribute_uro:urbanPlanningAreaName",
               "json_path" : "ancestors uro:StationSquareAttribute uro:urbanPlanningAreaName",
               "data_type" : "buffer"
            },
            {
               "attribute" : "uro:StationSquareAttribute_uro:enforcer",
               "json_path" : "ancestors uro:StationSquareAttribute uro:enforcer",
               "data_type" : "buffer"
            },
            {
               "attribute" : "uro:StationSquareAttribute_uro:dateOfDecision",
               "json_path" : "ancestors uro:StationSquareAttribute uro:dateOfDecision",
               "data_type" : "date"
            },
            {
               "attribute" : "uro:StationSquareAttribute_uro:dateOfRevision",
               "json_path" : "ancestors uro:StationSquareAttribute uro:dateOfRevision",
               "data_type" : "date"
            },
            {
               "attribute" : "uro:StationSquareAttribute_uro:areaPlanned",
               "json_path" : "ancestors uro:StationSquareAttribute uro:areaPlanned",
               "data_type" : "real64"
            },
            {
               "attribute" : "uro:StationSquareAttribute_uro:areaInService",
               "json_path" : "ancestors uro:StationSquareAttribute uro:areaInService",
               "data_type" : "real64"
            },
            {
               "attribute" : "uro:StationSquareAttribute_uro:remarks",
               "json_path" : "ancestors uro:StationSquareAttribute uro:remarks",
               "data_type" : "buffer"
            },
            {
               "attribute" : "uro:StationSquareAttribute_uro:status",
               "json_path" : "ancestors uro:StationSquareAttribute uro:status",
               "data_type" : "buffer"
            },
            {
               "attribute" : "uro:StationSquareAttribute_uro:areaImproved",
               "json_path" : "ancestors uro:StationSquareAttribute uro:areaImproved",
               "data_type" : "real64"
            },
            {
               "attribute" : "uro:StationSquareAttribute_uro:areaCompleted",
               "json_path" : "ancestors uro:StationSquareAttribute uro:areaCompleted",
               "data_type" : "real64"
            },
            {
               "attribute" : "uro:StationSquareAttribute_uro:projectStartDate",
               "json_path" : "ancestors uro:StationSquareAttribute uro:projectStartDate",
               "data_type" : "date"
            },
            {
               "attribute" : "uro:StationSquareAttribute_uro:projectEndDate",
               "json_path" : "ancestors uro:StationSquareAttribute uro:projectEndDate",
               "data_type" : "date"
            },
            {
               "attribute" : "uro:StationSquareAttribute_uro:isCompleted",
               "json_path" : "ancestors uro:StationSquareAttribute uro:isCompleted",
               "data_type" : "buffer"
            },
            {
               "attribute" : "uro:StationSquareAttribute_uro:isAuthorized",
               "json_path" : "ancestors uro:StationSquareAttribute uro:isAuthorized",
               "data_type" : "buffer"
            },
            {
               "attribute" : "uro:StationSquareAttribute_uro:purpose",
               "json_path" : "ancestors uro:StationSquareAttribute uro:purpose",
               "data_type" : "buffer"
            },
            {
               "attribute" : "uro:StationSquareAttribute_uro:note",
               "json_path" : "ancestors uro:StationSquareAttribute uro:note",
               "data_type" : "buffer"
            },
            {
               "attribute" : "uro:StationSquareAttribute_uro:station",
               "json_path" : "ancestors uro:StationSquareAttribute uro:station",
               "data_type" : "buffer"
            },
            {
               "attribute" : "uro:StationSquareAttribute_uro:route",
               "json_path" : "ancestors uro:StationSquareAttribute uro:route",
               "data_type" : "buffer"
            },
            {
               "attribute" : "uro:StationSquareAttribute_uro:railwayType",
               "json_path" : "ancestors uro:StationSquareAttribute uro:railwayType",
               "data_type" : "buffer"
            },
            {
               "attribute" : "uro:TerminalAttribute_uro:prefecture",
               "json_path" : "ancestors uro:TerminalAttribute uro:prefecture",
               "data_type" : "buffer"
            },
            {
               "attribute" : "uro:TerminalAttribute_uro:city",
               "json_path" : "ancestors uro:TerminalAttribute uro:city",
               "data_type" : "buffer"
            },
            {
               "attribute" : "uro:TerminalAttribute_uro:urbanPlanningAreaName",
               "json_path" : "ancestors uro:TerminalAttribute uro:urbanPlanningAreaName",
               "data_type" : "buffer"
            },
            {
               "attribute" : "uro:TerminalAttribute_uro:enforcer",
               "json_path" : "ancestors uro:TerminalAttribute uro:enforcer",
               "data_type" : "buffer"
            },
            {
               "attribute" : "uro:TerminalAttribute_uro:dateOfDecision",
               "json_path" : "ancestors uro:TerminalAttribute uro:dateOfDecision",
               "data_type" : "date"
            },
            {
               "attribute" : "uro:TerminalAttribute_uro:dateOfRevision",
               "json_path" : "ancestors uro:TerminalAttribute uro:dateOfRevision",
               "data_type" : "date"
            },
            {
               "attribute" : "uro:TerminalAttribute_uro:areaPlanned",
               "json_path" : "ancestors uro:TerminalAttribute uro:areaPlanned",
               "data_type" : "real64"
            },
            {
               "attribute" : "uro:TerminalAttribute_uro:areaInService",
               "json_path" : "ancestors uro:TerminalAttribute uro:areaInService",
               "data_type" : "real64"
            },
            {
               "attribute" : "uro:TerminalAttribute_uro:remarks",
               "json_path" : "ancestors uro:TerminalAttribute uro:remarks",
               "data_type" : "buffer"
            },
            {
               "attribute" : "uro:TerminalAttribute_uro:status",
               "json_path" : "ancestors uro:TerminalAttribute uro:status",
               "data_type" : "buffer"
            },
            {
               "attribute" : "uro:TerminalAttribute_uro:areaImproved",
               "json_path" : "ancestors uro:TerminalAttribute uro:areaImproved",
               "data_type" : "real64"
            },
            {
               "attribute" : "uro:TerminalAttribute_uro:areaCompleted",
               "json_path" : "ancestors uro:TerminalAttribute uro:areaCompleted",
               "data_type" : "real64"
            },
            {
               "attribute" : "uro:TerminalAttribute_uro:projectStartDate",
               "json_path" : "ancestors uro:TerminalAttribute uro:projectStartDate",
               "data_type" : "date"
            },
            {
               "attribute" : "uro:TerminalAttribute_uro:projectEndDate",
               "json_path" : "ancestors uro:TerminalAttribute uro:projectEndDate",
               "data_type" : "date"
            },
            {
               "attribute" : "uro:TerminalAttribute_uro:isCompleted",
               "json_path" : "ancestors uro:TerminalAttribute uro:isCompleted",
               "data_type" : "buffer"
            },
            {
               "attribute" : "uro:TerminalAttribute_uro:isAuthorized",
               "json_path" : "ancestors uro:TerminalAttribute uro:isAuthorized",
               "data_type" : "buffer"
            },
            {
               "attribute" : "uro:TerminalAttribute_uro:purpose",
               "json_path" : "ancestors uro:TerminalAttribute uro:purpose",
               "data_type" : "buffer"
            },
            {
               "attribute" : "uro:TerminalAttribute_uro:note",
               "json_path" : "ancestors uro:TerminalAttribute uro:note",
               "data_type" : "buffer"
            },
            {
               "attribute" : "uro:TerminalAttribute_uro:terminalType",
               "json_path" : "ancestors uro:TerminalAttribute uro:terminalType",
               "data_type" : "buffer"
            },
            {
               "attribute" : "uro:TerminalAttribute_uro:structure",
               "json_path" : "ancestors uro:TerminalAttribute uro:structure",
               "data_type" : "buffer"
            },
            {
               "attribute" : "uro:TerminalAttribute_uro:numberOfBerthsPlanned",
               "json_path" : "ancestors uro:TerminalAttribute uro:numberOfBerthsPlanned",
               "data_type" : "int16"
            },
            {
               "attribute" : "uro:TerminalAttribute_uro:numberOfBerthsInService",
               "json_path" : "ancestors uro:TerminalAttribute uro:numberOfBerthsInService",
               "data_type" : "int16"
            },
            {
               "attribute" : "uro:TerminalAttribute_uro:userType",
               "json_path" : "ancestors uro:TerminalAttribute uro:userType",
               "data_type" : "buffer"
            },
            {
               "attribute" : "uro:geometrySrcDescLod1",
               "json_path" : "ancestors uro:DataQualityAttribute uro:geometrySrcDescLod1",
               "data_type" : "buffer"
            },
            {
               "attribute" : "uro:lodType",
               "json_path" : "ancestors uro:DataQualityAttribute uro:lodType",
               "data_type" : "buffer"
            }
         ],
         "wwy/uro:Waterway" : [
            {
               "attribute" : "gml:name",
               "json_path" : "gml:name",
               "data_type" : "buffer"
            },
            {
               "attribute" : "core:creationDate",
               "json_path" : "core:creationDate",
               "data_type" : "date"
            },
            {
               "attribute" : "uro:routeId",
               "json_path" : "uro:WaterwayDetailAttribute uro:routeId",
               "data_type" : "buffer"
            },
            {
               "attribute" : "uro:routeDirection",
               "json_path" : "uro:WaterwayDetailAttribute uro:routeDirection",
               "data_type" : "buffer"
            },
            {
               "attribute" : "uro:minimumWidth",
               "json_path" : "uro:WaterwayDetailAttribute uro:minimumWidth",
               "data_type" : "real64"
            },
            {
               "attribute" : "uro:maximumWidth",
               "json_path" : "uro:WaterwayDetailAttribute uro:maximumWidth",
               "data_type" : "real64"
            },
            {
               "attribute" : "uro:length",
               "json_path" : "uro:WaterwayDetailAttribute uro:length",
               "data_type" : "real64"
            },
            {
               "attribute" : "uro:navigation",
               "json_path" : "uro:WaterwayDetailAttribute uro:navigation",
               "data_type" : "buffer"
            },
            {
               "attribute" : "uro:plannedDepth",
               "json_path" : "uro:WaterwayDetailAttribute uro:plannedDepth",
               "data_type" : "real64"
            },
            {
               "attribute" : "uro:speedLimit",
               "json_path" : "uro:WaterwayDetailAttribute uro:speedLimit",
               "data_type" : "real64"
            },
            {
               "attribute" : "uro:targetShipType",
               "json_path" : "uro:WaterwayDetailAttribute uro:targetShipType",
               "data_type" : "buffer"
            },
            {
               "attribute" : "uro:geometrySrcDescLod1",
               "json_path" : "uro:DataQualityAttribute uro:geometrySrcDescLod1",
               "data_type" : "buffer"
            },
            {
               "attribute" : "uro:lodType",
               "json_path" : "uro:DataQualityAttribute uro:lodType",
               "data_type" : "buffer"
            }
         ],
         "wwy/tran:TrafficArea" : [
            {
               "attribute" : "gml:name",
               "json_path" : "ancestors gml:name",
               "data_type" : "buffer"
            },
            {
               "attribute" : "core:creationDate",
               "json_path" : "ancestors core:creationDate",
               "data_type" : "date"
            },
            {
               "attribute" : "uro:routeId",
               "json_path" : "ancestors uro:WaterwayDetailAttribute uro:routeId",
               "data_type" : "buffer"
            },
            {
               "attribute" : "uro:routeDirection",
               "json_path" : "ancestors uro:WaterwayDetailAttribute uro:routeDirection",
               "data_type" : "buffer"
            },
            {
               "attribute" : "uro:minimumWidth",
               "json_path" : "ancestors uro:WaterwayDetailAttribute uro:minimumWidth",
               "data_type" : "real64"
            },
            {
               "attribute" : "uro:maximumWidth",
               "json_path" : "ancestors uro:WaterwayDetailAttribute uro:maximumWidth",
               "data_type" : "real64"
            },
            {
               "attribute" : "uro:length",
               "json_path" : "ancestors uro:WaterwayDetailAttribute uro:length",
               "data_type" : "real64"
            },
            {
               "attribute" : "uro:navigation",
               "json_path" : "ancestors uro:WaterwayDetailAttribute uro:navigation",
               "data_type" : "buffer"
            },
            {
               "attribute" : "uro:plannedDepth",
               "json_path" : "ancestors uro:WaterwayDetailAttribute uro:plannedDepth",
               "data_type" : "real64"
            },
            {
               "attribute" : "uro:speedLimit",
               "json_path" : "ancestors uro:WaterwayDetailAttribute uro:speedLimit",
               "data_type" : "real64"
            },
            {
               "attribute" : "uro:targetShipType",
               "json_path" : "ancestors uro:WaterwayDetailAttribute uro:targetShipType",
               "data_type" : "buffer"
            },
            {
               "attribute" : "uro:geometrySrcDescLod1",
               "json_path" : "ancestors uro:DataQualityAttribute uro:geometrySrcDescLod1",
               "data_type" : "buffer"
            },
            {
               "attribute" : "uro:lodType",
               "json_path" : "ancestors uro:DataQualityAttribute uro:lodType",
               "data_type" : "buffer"
            }
         ]
      }
- SourceDataset_XLSXR = $(FME_MF_DIR)テーブル_長寿命化計画対象施設.xlsx   # Source Microsoft Excel File(s)
- DestDataset_MVT_TILESET = $(FME_MF_DIR)output/trk/mvt   # Destination MVT Tileset Folder

Readers:
- XLSXR_1: XLSXR from $(SourceDataset_XLSXR)

Writers:
- CSV2_1: CSV2 to $(DEST_ROOT_FOLDER)
- CSV2_2: CSV2 to $(DestDataset_CSV2)
- MVT_TILESET_1: MVT_TILESET to $(DestDataset_MVT_TILESET)

Creator
    GEOMTYPE = Geometry Object
    NUM = 1
    CREATED -> PLATEAU4.AttributeReader_v2 [Initiator]
PLATEAU4.AttributeReader_v2
    ADD_NSPREFIX_TO_FEATURE_TYPES = Yes
    CITY_CODE = $(CITY_CODE)
    CODELISTS_FOLDER = $(CODELISTS_FOLDER)
    DATA_FILE = $(DATA_FILE)
    DICT_OF_ATTRS_TO_FLAT = $(DICT_OF_ATTRS_TO_FLAT)
    SCHEMAS_FOLDER = $(SCHEMAS_FOLDER)
    STD_SPEC_VERSION = 4
    TARGET_PACKAGES = tran,rwy,trk,squr,wwy
    FilePath -> Junction_5
    Schema -> Junction_9
    AttributeFeature -> AttributeManager_2
Junction_5
    -> StringSearcher
    -> AttributeManager
Note: code - メッシュコード / type － パッケージ名 / maxLod - 最大LOD / file - サブディレクトリ（階層）付のファイル名
maxLod (writer CSV2_1)
    attributes: code string, type string, maxLod string, file string
AttributeManager
    ATTR_TABLE:
      REMOVE _folder_root (buffer)
      REMOVE _udx_dirs (buffer)
      REMOVE _meshcode (buffer)
      REMOVE _city_code (varchar(200))
      REMOVE _city_name (buffer)
      REMOVE _feature_types (buffer)
      REMOVE _max_lod (int16)
    -> FeatureReader_CityGML [INITIATOR]
FeatureReader_CityGML
    ATTRIBUTES = core_CityModel,"gml_id,citygml_target_uri,gml_description,gml_name,citygml_city_object_member{}.xlink_href,citygml_appearance_member{}.xlink_href,gml_feature_member{}.xlink_href",tran_Road,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,uro_tran_dm_attribute{},citygml_class,citygml_class_codeSpace,citygml_function{},citygml_function{}.codeSpace,citygml_usage{},citygml_usage{}.codeSpace,citygml_traffic_area{}.xlink_href,citygml_auxiliary_traffic_area{}.xlink_href,citygml_level_of_detail{},uro_tran_data_quality_attribute{},uro_tran_facility_attribute{},uro_tran_facility_id_attribute{},uro_tran_facility_type_attribute{},uro_road_status{},uro_road_structure_attribute{},uro_traffic_volume_attribute{}"
    ATTRS_TO_EXPOSE = gml_id
    ATTR_ACCUM_MODE = Merge Initiator and Result
    ATTR_CONFLICT_RES = Use Result
    ATTR_IGNORE_NULLS = No
    CITYGML_ADD_NAMESPACE_PREFIX_TO_FEATURE_TYPES = Yes
    CITYGML_GENERIC_ATTRS_AS_FEATURES = No
    CITYGML_GENERIC_ATTRS_AS_SCHEMA_ATTRS = Yes
    CITYGML_LODS_TO_READ = 0 1 2 3 4
    CITYGML_MATERIAL_FEATURES = No
    CITYGML_MAX_ATTRIBUTES_PER_NESTED_ATTRIBUTE = 1
    CITYGML_ONLY_FEATURE_TYPES_IN_DATASET = YES
    CITYGML_SKIP_SCHEMA_LOCATION_IN_DATASET = No
    CITYGML_SRS_AXIS_ORDER = 2,1,3
    CITYGML_SUPPORTED_READER_ARCHIVE_EXTENSIONS = xml.gz,gml.gz
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    COORDSYS = EPSG:4326
    DATASET = @Value(_gml_path)
    FEATURETYPES = tran_Road tran_TrafficArea tran_AuxiliaryTrafficArea tran_Railway tran_Track tran_Square uro_Waterway
    FORMAT = CITYGML
    INTERACT = NONE
    OUTPUT_FEATURES_DISPLAY = Schema and Data Features
    <OTHER> -> TextureInterpretationCoercer
TextureInterpretationCoercer
    INTERPRETATION = RGB24
    WAIT_COERCE_COMPLETE = No
    -> Counter
Counter
    CNT_ATTR = _feature_index
    DOMAIN = counter
    SCOPE = Global
    START = 0
    -> FeatureMerger_3 [REQUESTOR]
Note: PythonCaller_mvt : Input
Junction_9
    -> Junction_10
    -> Junction_8
Note: AttributeReader : Schema
Junction_10
    -> PythonCaller_mvt
Junction_8
    -> PythonCaller_mvt_dmG
    -> PythonCaller_mvt_dmA
Note: _schema_definition = {package}/{prefix}:{feature type} / ex. tran/tran:Road / _mvt_layer = 名前空間プレフィクスを除くフィーチャータイプ名 / ex, Road, TrafficArea, AuxiliaryTrafficArea
AttributeManager_2
    ATTR_TABLE:
      RENAME_SET_VALUE _meshcode > meshcode (buffer)
      RENAME_SET_VALUE _city_code > city_code (buffer)
      RENAME_SET_VALUE _city_name > city_name (buffer)
      RENAME_SET_VALUE _feature_type > feature_type (buffer)
      RENAME_SET_VALUE _attributes > attributes (json)
      REMOVE _folder_root (buffer)
      REMOVE _udx_dirs (buffer)
      REMOVE _gml_path (buffer)
      REMOVE _num_lod0 (int64)
      REMOVE _num_lod1 (int64)
      REMOVE _num_lod2 (int64)
      REMOVE _num_lod3 (int64)
      REMOVE _num_lod4 (int64)
      REMOVE xml_id (uint32)
      REMOVE xml_parent_id (uint32)
      SET_TO _schema_definition (varchar(200)) = @Value(_folder_package)/@Value(feature_type)
      SET_TO _mvt_layer (varchar(200)) = @ReplaceRegularExpression(@Value(feature_type),.+:(.+),\1,caseSensitive=TRUE)
    -> Junction_11
Junction_11
    -> Junction_15
Junction_15
    -> FeatureMerger_3 [SUPPLIER]
FeatureMerger_3
    ATTR_ACCUM_MODE = Merge Supplier
    ATTR_CONFLICT_RES_LOOKUP = REQUESTOR_IF_CONFLICT
    GROUP_BY = _gml_filename
    IGNORE_NULLS = No
    JOIN_KEYS = @Value(gml_id) @Value(gml_id) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> PLATEAU4.LODSplitterWithDm_v2
Note: feature_type tran:Road / fme_feature_type tran_Road / _schema_definition tran/tran:Road
PLATEAU4.LODSplitterWithDm_v2
    JSON_ATTRIBUTES = @Value(attributes)
    SRS_AXIS_ORDER_DISPLAY = 2,1,3
    LOD0 -> Junction_3
    LOD1 -> Junction_3
    LOD2 -> Tester_lod2
    LOD3 -> Tester_lod3
    DmGeometricAttribute -> PROJReprojector_dmG
    DmAnnotation -> PROJReprojector_dmA
Note: 交通モデルのLOD2, LOD3では TrafficArea, AuxiliaryTrafficArea を可視化の対象とする。
Junction_3
    -> 2DForcer_lod0-2
2DForcer_lod0-2
    2D -> Sorter
Sorter
    SORT_PARM = _lod NUMERIC ASCENDING _schema_definition NATURAL ASCENDING _feature_index NUMERIC ASCENDING
    SORTED -> TranAreaRefiner
TranAreaRefiner
    _FEATURE_INDEX = @Value(_feature_index)
    _LOD = @Value(_lod)
    -> BulkAttributeRename_lod0-2
BulkAttributeRename_lod0-2: BulkAttributeRenamer
    ATTRCHOICE_ACTION = NONPROTECTEDFME
    CASE_DISP = YES
    MODE_CHOICE = RENAME
    PATTERN_ACTION_DISP = STRINGREPLACE
    REPLACE_PATTERN = :
    REPLACE_STR = _
    ATTRCHOICE = All Attributes
    -> AttributeManager_lod0-2
AttributeManager_lod0-2
    ATTR_TABLE:
      REMOVE _geometry_name (buffer)
      REMOVE _gml_path (buffer)
      REMOVE _feature_index (int64)
    USER_EXPOSED_ATTRIBUTES = uro_averageOutboundTravelSppedInCongetion,uro_averageInboundTravelSpeedNotCongesion
    -> PythonCaller_mvt
Note: スキーマ定義属性の作成
PythonCaller_mvt
    PYTHONSOURCE:
      import fme
      import fmeobjects, json

      class SchemaDefinitionSetterMVT(object):
          def __init__(self):
              self.flattenAttrs = None # {feature type : schema definition}
              self.featureTypes = set([]) # {set of tuple (feature type name without prefix, lod)}

          def input(self, feature):
              if not feature.isAttributeMissing('_flatten_attrs'):
                  self.flattenAttrs = json.loads(feature.getAttribute('_flatten_attrs'))

              else:
                  ftype = feature.getAttribute('_schema_definition')
                  lod = feature.getAttribute('_lod')

                  # (フィーチャータイプ, LOD)ごとに最初のフィーチャーにスキーマ属性を設定
                  # スキーマ定義名 = フィーチャータイプ名とする。
                  if (ftype, lod) not in self.featureTypes:
                      self.featureTypes.add((ftype, lod))

                      schema = [
                          # 全パッケージ共通属性
                          ('meshcode', 'fme_varchar(16)'),
                          ('feature_type', 'fme_buffer'),
                          ('city_code', 'fme_varchar(8)'),
                          ('city_name', 'fme_varchar(64)'),
                          ('gml_id', 'fme_varchar(64)'),
                          ('attributes', 'fme_json'),
                      ]

                      # フラットにする属性のスキーマ定義を追加
                      schemaDefs = self.flattenAttrs.get(ftype, [])
                      for obj in schemaDefs:
                          name = obj['attribute'].replace(':', '_')
                          type = 'fme_' + obj['data_type']
                          schema.append((name, type))

                      # スキーマ定義属性を設定
                      for i, (name, type) in enumerate(schema):
                          prefix = 'attribute{%d}' % i
                          feature.setAttribute(prefix + '.name', name)
                          feature.setAttribute(prefix + '.fme_data_type', type)

                      for i, gtype in enumerate(['fme_point', 'fme_line', 'fme_area']):
                          feature.setAttribute('fme_geometry{%d}' % i, gtype)

                  self.pyoutput(feature)

          def process_group(self):
              pass

          def close(self):
              pass

          def has_support_for(self, support_type):
              if support_type == fmeobjects.FME_SUPPORT_FEATURE_TABLE_SHIM:
                  return False
              return False
    PYTHONSYMBOL = SchemaDefinitionSetterMVT
    -> FeatureWriter_mvt_lod0-2 [2D]
    -> Junction_2
FeatureWriter_mvt_lod0-2 [off]
    DATASET = $(DEST_ROOT_FOLDER)/@Value(_folder_package)_lod@Value(_lod)
    DATASET_ATTR = _dataset
    FEATURE_TYPE_LIST_ATTR = _feature_types
    FORMAT = MVT_TILESET
    GROUP_BY = _lod
    MORE_SUMMARY_ATTRS = _folder_package
    MVT_TILESET_BUFFER_SIZE_CALCULATION = AUTO
    MVT_TILESET_COMPRESS = No
    MVT_TILESET_COORDINATE_SYSTEM_GRANULARITY = FEATURE
    MVT_TILESET_DESTINATION_DATASETTYPE_VALIDATION = Yes
    MVT_TILESET_EXTENT = 65536
    MVT_TILESET_LAYER_TYPE = overlay
    MVT_TILESET_MAXZOOM = 16
    MVT_TILESET_MAX_FEATURES = 2000000
    MVT_TILESET_MAX_SIZE = 5000000
    MVT_TILESET_MINZOOM = 8
    MVT_TILESET_OVERWRITE_DIRECTORY = Yes
    MVT_TILESET_SIMPLIFICATION = 0.0
    MVT_TILESET_SIMPLIFICATION_MAX_ZOOM = 0.0
    MVT_TILESET_TILE_EXTENSION = mvt
    MVT_TILESET_WRITE_NULLS = YES
    TOTAL_FEATURES_WRITTEN_ATTR = _total_features_written
    SUMMARY -> AttributeManager_mvt_lod0-2
AttributeManager_mvt_lod0-2
    ATTR_TABLE:
      SET_TO _package (varchar(200)) = @Value(_feature_types{0}._folder_package)
      SET_TO _lod (varchar(200)) = @Substring(@Value(_dataset),-1)
      SET_TO key (varchar(200)) = @Value(_package)_lod@Value(_lod)
      SET_TO suffix (varchar(200)) = mvt_lod@Value(_lod)
      RENAME_SET_VALUE _dataset > tileset_path (buffer)
      REMOVE _feature_types{}.count (uint64)
      REMOVE _feature_types{}.name (buffer)
      REMOVE _total_features_written (uint64)
      REMOVE _feature_types{}._folder_package (buffer)
    -> Junction
Note: AttributeKeeper : Input
Junction_2
    -> Junction_4
Note: PythonCaller_mvt : Output
Junction_4
    -> AttributeExposer
AttributeExposer
    ATTR_TABLE = gml_parent_id,
    -> AttributeKeeper
AttributeKeeper
    CREATE_BULK_MODE_FEATURES = NO
    KEEP_ATTRS = gml_parent_id,_folder_package
    -> FeatureMerger [REQUESTOR]
Note: 標高 -> 楕円体高
CsmapReprojector_lod3
    DEST = EPSG:4326
    GEOID_HEIGHT_GRID = $(GEOID_HEIGHT_GRID)
    INTERPOLATION_TYPE = ,NearestNeighbor
    RASTER_CELL_SIZE_LOOKUP = ,PreserveCells
    RASTER_TOLERANCE = 0.0
    SOURCE = EPSG:4326
    VERTICAL_HANDLING_LOOKUP = 3D_ORTHOMETRIC_TO_ELLIPSOID
    INTERPOLATION_TYPE_NAME = Nearest Neighbor
    RASTER_CELL_SIZE = Preserve Cells
    VERTICAL_HANDLING = Orthometric height -> Geocentric or ellipsoid height
    REPROJECTED -> AttributeManager_lod3
AttributeManager_lod3
    USER_EXPOSED_ATTRIBUTES = uro:averageOutboundTravelSppedInCongetion,uro:averageInboundTravelSpeedNotCongesion,_geometry_name,_lod,_folder_package,_gml_path,_gml_filename,gml_id,_feature_index,meshcode,city_code,city_name,feature_type,attributes,_mvt_layername,gml:name,core:creationDate,tran:class,tran:Road_tran:function,tran:function,tran:surfaceMaterial,tran:usage,uro:RoadStructureAttribute_uro:widthType,uro:RoadStructureAttribute_uro:width,uro:RoadStructureAttribute_uro:numberOfLanes,uro:RoadStructureAttribute_uro:sectionType,uro:TrafficVolumeAttribute_uro:sectionID,uro:TrafficVolumeAttribute_uro:routeName,uro:TrafficVolumeAttribute_uro:weekday12hourTrafficVolume,uro:TrafficVolumeAttribute_uro:weekday24hourTrafficVolume,uro:TrafficVolumeAttribute_uro:largeVehicleRate,uro:TrafficVolumeAttribute_uro:congestionRate,uro:TrafficVolumeAttribute_uro:averageTravelSpeedInCongestion,uro:TrafficVolumeAttribute_uro:averageInboundTravelSpeedInCongestion,uro:TrafficVolumeAttribute_uro:averageOutboundTravelSpeedInCongestion,uro:TrafficVolumeAttribute_uro:averageInboundTravelSpeedNotCongestion,uro:TrafficVolumeAttribute_uro:averageOutboundTravelSpeedNotCongestion,uro:TrafficVolumeAttribute_uro:observationPointName,uro:TrafficVolumeAttribute_uro:reference,uro:TrafficVolumeAttribute_uro:surveyYear,uro:geometrySrcDescLod1,uro:lodType,uro:numberOfLanes
    -> SchemaDefinitionSetter
SchemaDefinitionSetter
    SCHEMA_DEFS_SON:
      {
         "tran" : [
            {
               "attribute" : "core:creationDate",
               "data_type" : "date"
            },
            {
               "attribute" : "tran:class",
               "data_type" : "buffer"
            },
            {
               "attribute" : "tran:Road_tran:function",
               "data_type" : "buffer"
            },
            {
               "attribute" : "tran:function",
               "data_type" : "buffer"
            },
            {
               "attribute" : "uro:numberOfLanes",
               "data_type" : "int16"
            },
            {
               "attribute" : "tran:surfaceMaterial",
               "data_type" : "buffer"
            },
            {
               "attribute" : "tran:usage",
               "data_type" : "buffer"
            },
            {
               "attribute" : "uro:RoadStructureAttribute_uro:widthType",
               "data_type" : "buffer"
            },
            {
               "attribute" : "uro:RoadStructureAttribute_uro:width",
               "data_type" : "real64"
            },
            {
               "attribute" : "uro:RoadStructureAttribute_uro:numberOfLanes",
               "data_type" : "int16"
            },
            {
               "attribute" : "uro:RoadStructureAttribute_uro:sectionType",
               "data_type" : "buffer"
            },
            {
               "attribute" : "uro:TrafficVolumeAttribute_uro:sectionID",
               "data_type" : "buffer"
            },
            {
               "attribute" : "uro:TrafficVolumeAttribute_uro:routeName",
               "data_type" : "buffer"
            },
            {
               "attribute" : "uro:TrafficVolumeAttribute_uro:weekday12hourTrafficVolume",
               "data_type" : "real64"
            },
            {
               "attribute" : "uro:TrafficVolumeAttribute_uro:weekday24hourTrafficVolume",
               "data_type" : "real64"
            },
            {
               "attribute" : "uro:TrafficVolumeAttribute_uro:largeVehicleRate",
               "data_type" : "real64"
            },
            {
               "attribute" : "uro:TrafficVolumeAttribute_uro:congestionRate",
               "data_type" : "real64"
            },
            {
               "attribute" : "uro:TrafficVolumeAttribute_uro:averageTravelSpeedInCongestion",
               "data_type" : "real64"
            },
            {
               "attribute" : "uro:TrafficVolumeAttribute_uro:averageInboundTravelSpeedInCongestion",
               "data_type" : "real64"
            },
            {
               "attribute" : "uro:TrafficVolumeAttribute_uro:averageOutboundTravelSpeedInCongestion",
               "data_type" : "real64"
            },
            {
               "attribute" : "uro:TrafficVolumeAttribute_uro:averageInboundTravelSpeedNotCongestion",
               "data_type" : "real64"
            },
            {
               "attribute" : "uro:TrafficVolumeAttribute_uro:averageOutboundTravelSpeedNotCongestion",
               "data_type" : "real64"
            },
            {
               "attribute" : "uro:TrafficVolumeAttribute_uro:observationPointName",
               "data_type" : "buffer"
            },
            {
               "attribute" : "uro:TrafficVolumeAttribute_uro:reference",
               "data_type" : "buffer"
            },
            {
               "attribute" : "uro:TrafficVolumeAttribute_uro:surveyYear",
               "data_type" : "int16"
            },
            {
               "attribute" : "uro:geometrySrcDescLod1",
               "data_type" : "buffer"
            },
            {
               "attribute" : "uro:lodType",
               "data_type" : "buffer"
            },
            {
               "attribute" : "gml:name",
               "data_type" : "buffer"
            }
         ],
         "rwy" : [
            {
               "attribute" : "core:creationDate",
               "data_type" : "date"
            },
            {
               "attribute" : "tran:class",
               "data_type" : "buffer"
            },
            {
               "attribute" : "tran:function",
               "data_type" : "buffer"
            },
            {
               "attribute" : "uro:operatorType",
               "data_type" : "buffer"
            },
            {
               "attribute" : "uro:operator",
               "data_type" : "buffer"
            },
            {
               "attribute" : "uro:railwayType",
               "data_type" : "buffer"
            },
            {
               "attribute" : "uro:startStation",
               "data_type" : "buffer"
            },
            {
               "attribute" : "uro:endStation",
               "data_type" : "buffer"
            },
            {
               "attribute" : "uro:routeName",
               "data_type" : "buffer"
            },
            {
               "attribute" : "uro:directionType",
               "data_type" : "buffer"
            },
            {
               "attribute" : "uro:trackType",
               "data_type" : "buffer"
            },
            {
               "attribute" : "uro:startPost",
               "data_type" : "buffer"
            },
            {
               "attribute" : "uro:endPost",
               "data_type" : "buffer"
            },
            {
               "attribute" : "uro:alignmentType",
               "data_type" : "buffer"
            },
            {
               "attribute" : "uro:geometrySrcDescLod1",
               "data_type" : "buffer"
            },
            {
               "attribute" : "uro:lodType",
               "data_type" : "buffer"
            },
            {
               "attribute" : "gml:name",
               "data_type" : "buffer"
            }
         ],
         "trk" : [
            {
               "attribute" : "core:creationDate",
               "data_type" : "date"
            },
            {
               "attribute" : "tran:class",
               "data_type" : "buffer"
            },
            {
               "attribute" : "tran:Track_tran:function",
               "data_type" : "buffer"
            },
            {
               "attribute" : "tran:function",
               "data_type" : "buffer"
            },
            {
               "attribute" : "tran:usage",
               "data_type" : "buffer"
            },
            {
               "attribute" : "uro:geometrySrcDescLod1",
               "data_type" : "buffer"
            },
            {
               "attribute" : "uro:lodType",
               "data_type" : "buffer"
            },
            {
               "attribute" : "gml:name",
               "data_type" : "buffer"
            }
         ],
         "squr" : [
            {
               "attribute" : "core:creationDate",
               "data_type" : "date"
            },
            {
               "attribute" : "tran:class",
               "data_type" : "buffer"
            },
            {
               "attribute" : "tran:Square_tran:function",
               "data_type" : "buffer"
            },
            {
               "attribute" : "tran:function",
               "data_type" : "buffer"
            },
            {
               "attribute" : "uro:SquareUrbanPlanAttribute_uro:prefecture",
               "data_type" : "buffer"
            },
            {
               "attribute" : "uro:SquareUrbanPlanAttribute_uro:city",
               "data_type" : "buffer"
            },
            {
               "attribute" : "uro:SquareUrbanPlanAttribute_uro:urbanPlanningAreaName",
               "data_type" : "buffer"
            },
            {
               "attribute" : "uro:SquareUrbanPlanAttribute_uro:enforcer",
               "data_type" : "buffer"
            },
            {
               "attribute" : "uro:SquareUrbanPlanAttribute_uro:dateOfDecision",
               "data_type" : "date"
            },
            {
               "attribute" : "uro:SquareUrbanPlanAttribute_uro:dateOfRevision",
               "data_type" : "date"
            },
            {
               "attribute" : "uro:SquareUrbanPlanAttribute_uro:areaPlanned",
               "data_type" : "real64"
            },
            {
               "attribute" : "uro:SquareUrbanPlanAttribute_uro:areaInService",
               "data_type" : "real64"
            },
            {
               "attribute" : "uro:SquareUrbanPlanAttribute_uro:remarks",
               "data_type" : "buffer"
            },
            {
               "attribute" : "uro:SquareUrbanPlanAttribute_uro:status",
               "data_type" : "buffer"
            },
            {
               "attribute" : "uro:SquareUrbanPlanAttribute_uro:areaImproved",
               "data_type" : "real64"
            },
            {
               "attribute" : "uro:SquareUrbanPlanAttribute_uro:areaCompleted",
               "data_type" : "real64"
            },
            {
               "attribute" : "uro:SquareUrbanPlanAttribute_uro:projectStartDate",
               "data_type" : "date"
            },
            {
               "attribute" : "uro:SquareUrbanPlanAttribute_uro:projectEndDate",
               "data_type" : "date"
            },
            {
               "attribute" : "uro:SquareUrbanPlanAttribute_uro:isCompleted",
               "data_type" : "buffer"
            },
            {
               "attribute" : "uro:SquareUrbanPlanAttribute_uro:isAuthorized",
               "data_type" : "buffer"
            },
            {
               "attribute" : "uro:SquareUrbanPlanAttribute_uro:purpose",
               "data_type" : "buffer"
            },
            {
               "attribute" : "uro:SquareUrbanPlanAttribute_uro:note",
               "data_type" : "buffer"
            },
            {
               "attribute" : "uro:StationSquareAttribute_uro:prefecture",
               "data_type" : "buffer"
            },
            {
               "attribute" : "uro:StationSquareAttribute_uro:city",
               "data_type" : "buffer"
            },
            {
               "attribute" : "uro:StationSquareAttribute_uro:urbanPlanningAreaName",
               "data_type" : "buffer"
            },
            {
               "attribute" : "uro:StationSquareAttribute_uro:enforcer",
               "data_type" : "buffer"
            },
            {
               "attribute" : "uro:StationSquareAttribute_uro:dateOfDecision",
               "data_type" : "date"
            },
            {
               "attribute" : "uro:StationSquareAttribute_uro:dateOfRevision",
               "data_type" : "date"
            },
            {
               "attribute" : "uro:StationSquareAttribute_uro:areaPlanned",
               "data_type" : "real64"
            },
            {
               "attribute" : "uro:StationSquareAttribute_uro:areaInService",
               "data_type" : "real64"
            },
            {
               "attribute" : "uro:StationSquareAttribute_uro:remarks",
               "data_type" : "buffer"
            },
            {
               "attribute" : "uro:StationSquareAttribute_uro:status",
               "data_type" : "buffer"
            },
            {
               "attribute" : "uro:StationSquareAttribute_uro:areaImproved",
               "data_type" : "real64"
            },
            {
               "attribute" : "uro:StationSquareAttribute_uro:areaCompleted",
               "data_type" : "real64"
            },
            {
               "attribute" : "uro:StationSquareAttribute_uro:projectStartDate",
               "data_type" : "date"
            },
            {
               "attribute" : "uro:StationSquareAttribute_uro:projectEndDate",
               "data_type" : "date"
            },
            {
               "attribute" : "uro:StationSquareAttribute_uro:isCompleted",
               "data_type" : "buffer"
            },
            {
               "attribute" : "uro:StationSquareAttribute_uro:isAuthorized",
               "data_type" : "buffer"
            },
            {
               "attribute" : "uro:StationSquareAttribute_uro:purpose",
               "data_type" : "buffer"
            },
            {
               "attribute" : "uro:StationSquareAttribute_uro:note",
               "data_type" : "buffer"
            },
            {
               "attribute" : "uro:StationSquareAttribute_uro:station",
               "data_type" : "buffer"
            },
            {
               "attribute" : "uro:StationSquareAttribute_uro:route",
               "data_type" : "buffer"
            },
            {
               "attribute" : "uro:StationSquareAttribute_uro:railwayType",
               "data_type" : "buffer"
            },
            {
               "attribute" : "uro:TerminalAttribute_uro:prefecture",
               "data_type" : "buffer"
            },
            {
               "attribute" : "uro:TerminalAttribute_uro:city",
               "data_type" : "buffer"
            },
            {
               "attribute" : "uro:TerminalAttribute_uro:urbanPlanningAreaName",
               "data_type" : "buffer"
            },
            {
               "attribute" : "uro:TerminalAttribute_uro:enforcer",
               "data_type" : "buffer"
            },
            {
               "attribute" : "uro:TerminalAttribute_uro:dateOfDecision",
               "data_type" : "date"
            },
            {
               "attribute" : "uro:TerminalAttribute_uro:dateOfRevision",
               "data_type" : "date"
            },
            {
               "attribute" : "uro:TerminalAttribute_uro:areaPlanned",
               "data_type" : "real64"
            },
            {
               "attribute" : "uro:TerminalAttribute_uro:areaInService",
               "data_type" : "real64"
            },
            {
               "attribute" : "uro:TerminalAttribute_uro:remarks",
               "data_type" : "buffer"
            },
            {
               "attribute" : "uro:TerminalAttribute_uro:status",
               "data_type" : "buffer"
            },
            {
               "attribute" : "uro:TerminalAttribute_uro:areaImproved",
               "data_type" : "real64"
            },
            {
               "attribute" : "uro:TerminalAttribute_uro:areaCompleted",
               "data_type" : "real64"
            },
            {
               "attribute" : "uro:TerminalAttribute_uro:projectStartDate",
               "data_type" : "date"
            },
            {
               "attribute" : "uro:TerminalAttribute_uro:projectEndDate",
               "data_type" : "date"
            },
            {
               "attribute" : "uro:TerminalAttribute_uro:isCompleted",
               "data_type" : "buffer"
            },
            {
               "attribute" : "uro:TerminalAttribute_uro:isAuthorized",
               "data_type" : "buffer"
            },
            {
               "attribute" : "uro:TerminalAttribute_uro:purpose",
               "data_type" : "buffer"
            },
            {
               "attribute" : "uro:TerminalAttribute_uro:note",
               "data_type" : "buffer"
            },
            {
               "attribute" : "uro:TerminalAttribute_uro:terminalType",
               "data_type" : "buffer"
            },
            {
               "attribute" : "uro:TerminalAttribute_uro:structure",
               "data_type" : "buffer"
            },
            {
               "attribute" : "uro:TerminalAttribute_uro:numberOfBerthsPlanned",
               "data_type" : "int16"
            },
            {
               "attribute" : "uro:TerminalAttribute_uro:numberOfBerthsInService",
               "data_type" : "int16"
            },
            {
               "attribute" : "uro:TerminalAttribute_uro:userType",
               "data_type" : "buffer"
            },
            {
               "attribute" : "uro:geometrySrcDescLod1",
               "data_type" : "buffer"
            },
            {
               "attribute" : "uro:lodType",
               "data_type" : "buffer"
            },
            {
               "attribute" : "gml:name",
               "data_type" : "buffer"
            }
         ],
         "wwy" : [
            {
               "attribute" : "core:creationDate",
               "data_type" : "date"
            },
            {
               "attribute" : "uro:routeId",
               "data_type" : "buffer"
            },
            {
               "attribute" : "uro:routeDirection",
               "data_type" : "buffer"
            },
            {
               "attribute" : "uro:minimumWidth",
               "data_type" : "real64"
            },
            {
               "attribute" : "uro:maximumWidth",
               "data_type" : "real64"
            },
            {
               "attribute" : "uro:length",
               "data_type" : "real64"
            },
            {
               "attribute" : "uro:navigation",
               "data_type" : "buffer"
            },
            {
               "attribute" : "uro:plannedDepth",
               "data_type" : "real64"
            },
            {
               "attribute" : "uro:speedLimit",
               "data_type" : "real64"
            },
            {
               "attribute" : "uro:targetShipType",
               "data_type" : "buffer"
            },
            {
               "attribute" : "uro:geometrySrcDescLod1",
               "data_type" : "buffer"
            },
            {
               "attribute" : "uro:lodType",
               "data_type" : "buffer"
            },
            {
               "attribute" : "gml:name",
               "data_type" : "buffer"
            }
         ]
      }
    TARGET_PACKAGE = @Value(_folder_package)
    -> AppearanceSetter [GEOMETRY]
AppearanceSetter
    APPEARANCE_DEFINITION_STORAGE = CREATE
    GQUERY:
      for $geom in //geometry
      where $geom/count(parent::geometry) = 0
      return number($geom/@fme_id)
    SHININESS = 1
    SIDE_OPTION = BOTH
    SPECULAR_COLOR = 1,1,1
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
    -> FeatureWriter_3dtiles_lod3 [tran_lod3]
FeatureWriter_3dtiles_lod3 [off]
    CESIUM3DTILES_ALLOW_MIXED_GEOM_TILESETS = NO
    CESIUM3DTILES_COORDINATE_SYSTEM_GRANULARITY = FEATURE
    CESIUM3DTILES_CREATE_ATLAS_TEXTURES = YES
    CESIUM3DTILES_DEFAULT_CRS = EPSG:4326
    CESIUM3DTILES_MAX_FACES_PER_TILE = 10000
    CESIUM3DTILES_TEXTURE_FORMAT_CHOICES = WEBP
    DATASET = $(DEST_ROOT_FOLDER)
    DATASET_ATTR = _dataset
    FEATURE_TYPE_LIST_ATTR = _feature_types
    FORMAT = CESIUM3DTILES
    MORE_SUMMARY_ATTRS = _folder_package
    TOTAL_FEATURES_WRITTEN_ATTR = _total_features_written
    SUMMARY -> AttributeManager_3dtiles_lod3
AttributeManager_3dtiles_lod3
    ATTR_TABLE:
      SET_TO _package (varchar(200)) = @Value(_feature_types{0}._folder_package)
      SET_TO key (varchar(200)) = @Value(_package)_lod3
      SET_TO suffix (varchar(200)) = 3dtiles_lod3
      SET_TO tileset_path (varchar(200)) = @Value(_dataset)/@Value(_feature_types{0}.name)
      REMOVE _feature_types{}.count (uint64)
      REMOVE _feature_types{}.name (buffer)
      REMOVE _dataset (buffer)
      REMOVE _total_features_written (uint64)
      REMOVE _feature_types{}._folder_package (buffer)
    -> Junction
Note: EPSG:3857に変換
PROJReprojector_dmG
    DEST = EPSG:3857
    INTERPOLATION_TYPE = ,NearestNeighbor
    RASTER_CELL_SIZE_LOOKUP = ,PreserveCells
    RASTER_TOLERANCE = 0.0
    TRANSFORM_TYPE = Automatic Transformation
    INTERPOLATION_TYPE_NAME = Nearest Neighbor
    RASTER_CELL_SIZE = Preserve Cells
    REPROJECTED -> BulkAttributeRenamer_dmG
BulkAttributeRenamer_dmG
    ATTRCHOICE_ACTION = NONPROTECTEDFME
    CASE_DISP = YES
    MODE_CHOICE = RENAME
    PATTERN_ACTION_DISP = STRINGREPLACE
    REPLACE_PATTERN = :
    REPLACE_STR = _
    ATTRCHOICE = All Attributes
    -> AttributeManager_dmG
AttributeManager_dmG
    ATTR_TABLE:
      REMOVE dm_attributes_xml (buffer)
      RENAME_SET_VALUE dm_attributes_json > dm_attributes (varchar(200))
      REMOVE _geometry_name (buffer)
      REMOVE _lod (varchar(200))
      REMOVE _gml_path (buffer)
      REMOVE _gml_filename (buffer)
      SET_TO _key_suffix (varchar(200)) = dm_geometric_attributes
      SET_TO _feature_type_without_prefix (varchar(200)) = @ReplaceRegularExpression(@Value(feature_type),.+:(.+),\1,caseSensitive=TRUE)
    -> PythonCaller_mvt_dmG
Note: スキーマ定義属性の作成
PythonCaller_mvt_dmG
    PYTHONSOURCE:
      import fme
      import fmeobjects, json

      class SchemaDefinitionSetterMVT(object):
          def __init__(self):
              self.flattenAttrs = None # {feature type : schema definition}
              self.featureTypes = set([]) # {set of feature type names without prefix}

          def input(self, feature):
              if not feature.isAttributeMissing('_flatten_attrs'):
                  self.flattenAttrs = json.loads(feature.getAttribute('_flatten_attrs'))

              else:
                  ftype = feature.getAttribute('_schema_definition')

                  # フィーチャータイプごとに最初のフィーチャーにスキーマ属性を設定
                  # スキーマ定義名 = フィーチャータイプ名とする。
                  if ftype not in self.featureTypes:
                      self.featureTypes.add(ftype)

                      schema = [
                          # 全パッケージ共通属性
                          ('meshcode', 'fme_varchar(16)'),
                          ('feature_type', 'fme_buffer'),
                          ('city_code', 'fme_varchar(8)'),
                          ('city_name', 'fme_varchar(64)'),
                          ('gml_id', 'fme_varchar(64)'),
                          ('attributes', 'fme_json'),
                      ]

                      # フラットにする属性のスキーマ定義を追加
                      schemaDefs = self.flattenAttrs.get(ftype, [])
                      for obj in schemaDefs:
                          name = obj['attribute'].replace(':', '_')
                          type = 'fme_' + obj['data_type']
                          schema.append((name, type))

                      # スキーマ定義属性を設定
                      for i, (name, type) in enumerate(schema):
                          prefix = 'attribute{%d}' % i
                          feature.setAttribute(prefix + '.name', name)
                          feature.setAttribute(prefix + '.fme_data_type', type)

                      for i, gtype in enumerate(['fme_point', 'fme_line', 'fme_area']):
                          feature.setAttribute('fme_geometry{%d}' % i, gtype)

                  self.pyoutput(feature)

          def process_group(self):
              pass

          def close(self):
              pass

          def has_support_for(self, support_type):
              if support_type == fmeobjects.FME_SUPPORT_FEATURE_TABLE_SHIM:
                  return False
              return False
    PYTHONSYMBOL = SchemaDefinitionSetterMVT
    -> FeatureWriter_mvt_dmG [2D]
FeatureWriter_mvt_dmG [off]
    DATASET = $(DEST_ROOT_FOLDER)/@Value(_folder_package)_dm_geometric_attributes
    DATASET_ATTR = _dataset
    FEATURE_TYPE_LIST_ATTR = _feature_types
    FORMAT = MVT_TILESET
    MORE_SUMMARY_ATTRS = _folder_package _key_suffix
    MVT_TILESET_BUFFER_SIZE_CALCULATION = AUTO
    MVT_TILESET_COMPRESS = No
    MVT_TILESET_COORDINATE_SYSTEM_GRANULARITY = FEATURE
    MVT_TILESET_DESTINATION_DATASETTYPE_VALIDATION = Yes
    MVT_TILESET_EXTENT = 65536
    MVT_TILESET_LAYER_TYPE = overlay
    MVT_TILESET_MAXZOOM = 16
    MVT_TILESET_MAX_FEATURES = 2000000
    MVT_TILESET_MAX_SIZE = 5000000
    MVT_TILESET_MINZOOM = 8
    MVT_TILESET_OVERWRITE_DIRECTORY = Yes
    MVT_TILESET_SIMPLIFICATION = 0.0
    MVT_TILESET_SIMPLIFICATION_MAX_ZOOM = 0.0
    MVT_TILESET_TILE_EXTENSION = mvt
    MVT_TILESET_WRITE_NULLS = YES
    TOTAL_FEATURES_WRITTEN_ATTR = _total_features_written
    SUMMARY -> ListIndexer
Note: EPSG:3857に変換
PROJReprojector_dmA
    DEST = EPSG:3857
    INTERPOLATION_TYPE = ,NearestNeighbor
    RASTER_CELL_SIZE_LOOKUP = ,PreserveCells
    RASTER_TOLERANCE = 0.0
    TRANSFORM_TYPE = Automatic Transformation
    INTERPOLATION_TYPE_NAME = Nearest Neighbor
    RASTER_CELL_SIZE = Preserve Cells
    REPROJECTED -> BulkAttributeRenamer_dmA
BulkAttributeRenamer_dmA
    ATTRCHOICE_ACTION = NONPROTECTEDFME
    CASE_DISP = YES
    MODE_CHOICE = RENAME
    PATTERN_ACTION_DISP = STRINGREPLACE
    REPLACE_PATTERN = :
    REPLACE_STR = _
    ATTRCHOICE = All Attributes
    -> AttributeManager_dmA
AttributeManager_dmA
    ATTR_TABLE:
      REMOVE dm_attributes_xml (buffer)
      RENAME_SET_VALUE dm_attributes_json > dm_attributes (varchar(200))
      REMOVE _geometry_name (buffer)
      REMOVE _lod (varchar(200))
      REMOVE _gml_path (buffer)
      REMOVE _gml_filename (buffer)
      SET_TO _key_suffix (varchar(200)) = dm_annotations
      SET_TO _feature_type_without_prefix (varchar(200)) = @ReplaceRegularExpression(@Value(feature_type),.+:(.+),\1,caseSensitive=TRUE)
    USER_EXPOSED_ATTRIBUTES = dm_feature_type,dm_attributes_xml,dm_attributes_json,dm_dmCode,dm_dmCode_code,dm_geometryType,dm_geometryType_code,dm_shapeType,dm_shapeType_code,dm_label,dm_isVertical,dm_size,dm_orientation,dm_linewidth,dm_spacing,_geometry_name,_lod,_folder_package,_gml_path,_gml_filename,_epsg_code,gml_id,fme_feature_type,_feature_index,meshcode,city_code,city_name,feature_type,attributes,gml:name,frn:function,uro:occupierType,uro:occupierName,_feature_type_without_prefix
    -> PythonCaller_mvt_dmA
Note: スキーマ定義属性の作成
PythonCaller_mvt_dmA
    PYTHONSOURCE:
      import fme
      import fmeobjects, json

      class SchemaDefinitionSetterMVT(object):
          def __init__(self):
              self.flattenAttrs = None # {feature type : schema definition}
              self.featureTypes = set([]) # {set of feature type names without prefix}

          def input(self, feature):
              if not feature.isAttributeMissing('_flatten_attrs'):
                  self.flattenAttrs = json.loads(feature.getAttribute('_flatten_attrs'))

              else:
                  ftype = feature.getAttribute('_schema_definition')

                  # フィーチャータイプごとに最初のフィーチャーにスキーマ属性を設定
                  # スキーマ定義名 = フィーチャータイプ名とする。
                  if ftype not in self.featureTypes:
                      self.featureTypes.add(ftype)

                      schema = [
                          # 全パッケージ共通属性
                          ('meshcode', 'fme_varchar(16)'),
                          ('feature_type', 'fme_buffer'),
                          ('city_code', 'fme_varchar(8)'),
                          ('city_name', 'fme_varchar(64)'),
                          ('gml_id', 'fme_varchar(64)'),
                          ('attributes', 'fme_json'),
                      ]

                      # フラットにする属性のスキーマ定義を追加
                      schemaDefs = self.flattenAttrs.get(ftype, [])
                      for obj in schemaDefs:
                          name = obj['attribute'].replace(':', '_')
                          type = 'fme_' + obj['data_type']
                          schema.append((name, type))

                      # スキーマ定義属性を設定
                      for i, (name, type) in enumerate(schema):
                          prefix = 'attribute{%d}' % i
                          feature.setAttribute(prefix + '.name', name)
                          feature.setAttribute(prefix + '.fme_data_type', type)

                      for i, gtype in enumerate(['fme_point', 'fme_line', 'fme_area']):
                          feature.setAttribute('fme_geometry{%d}' % i, gtype)

                  self.pyoutput(feature)

          def process_group(self):
              pass

          def close(self):
              pass

          def has_support_for(self, support_type):
              if support_type == fmeobjects.FME_SUPPORT_FEATURE_TABLE_SHIM:
                  return False
              return False
    PYTHONSYMBOL = SchemaDefinitionSetterMVT
    -> FeatureWriter_mvt_dmA [2D]
FeatureWriter_mvt_dmA [off]
    DATASET = $(DEST_ROOT_FOLDER)/@Value(_folder_package)_gm_annotation
    DATASET_ATTR = _dataset
    FEATURE_TYPE_LIST_ATTR = _feature_types
    FORMAT = MVT_TILESET
    MORE_SUMMARY_ATTRS = _folder_package _key_suffix
    MVT_TILESET_BUFFER_SIZE_CALCULATION = AUTO
    MVT_TILESET_COMPRESS = No
    MVT_TILESET_COORDINATE_SYSTEM_GRANULARITY = FEATURE
    MVT_TILESET_DESTINATION_DATASETTYPE_VALIDATION = Yes
    MVT_TILESET_EXTENT = 65536
    MVT_TILESET_LAYER_TYPE = overlay
    MVT_TILESET_MAXZOOM = 16
    MVT_TILESET_MAX_FEATURES = 2000000
    MVT_TILESET_MAX_SIZE = 5000000
    MVT_TILESET_MINZOOM = 8
    MVT_TILESET_OVERWRITE_DIRECTORY = Yes
    MVT_TILESET_SIMPLIFICATION = 0.0
    MVT_TILESET_SIMPLIFICATION_MAX_ZOOM = 0.0
    MVT_TILESET_TILE_EXTENSION = mvt
    MVT_TILESET_WRITE_NULLS = YES
    TOTAL_FEATURES_WRITTEN_ATTR = _total_features_written
    SUMMARY -> ListIndexer
ListIndexer
    INDEX = 0
    LIST_ATTR = _feature_types{}
    -> AttributeManager_mvt_DM
AttributeManager_mvt_DM
    ATTR_TABLE:
      SET_TO key (varchar(200)) = @Value(_folder_package)_@Value(_key_suffix)
      RENAME_SET_VALUE _key_suffix > suffix (buffer)
      RENAME_SET_VALUE _dataset > tileset_path (buffer)
      REMOVE _feature_types{}.count (uint64)
      REMOVE _feature_types{}.name (buffer)
      REMOVE _feature_types{}._folder_package (buffer)
      REMOVE _feature_types{}._key_suffix (buffer)
      REMOVE _total_features_written (uint64)
      REMOVE count (uint64)
      REMOVE name (buffer)
      REMOVE _folder_package (buffer)
    -> Junction
Junction
    -> summary (writer CSV2_1)
summary (writer CSV2_1)
    attributes: key string, suffix string, tileset_path string
公園施設長寿命化計画対象（R6年度全体） (reader XLSXR_1)
    attributes: gml:id char(41), 公園コード char(3), 公園名 char(24), 公園種別 char(6), 施設コード char(7), 公園施設種類【選択】 char(15), 公園施設名【選択】 char(21), 公園施設名（任意） char(48), 具体的施設名称 char(63), 数量（数値） number(7,1), 数量（単位【選択】) char(3), 規模 char(11), 主要部材【選択】 char(18), 主要部材（任意） char(39), 設置年度 number(4,0), 経過年数 number(2,0), 処分制限期間など number(2,0), 使用見込み期間 number(2,0), 健全度調査以前に実施した補修の有無（有無） char(1), 健全度調査以前に実施した補修の有無（年度） char(1), 健全度調査（年度） number(4,0), 健全度調査（劣化状況） char(285), 健全度調査（健全度） char(3), 健全度調査（緊急度） char(3), 管理類型 char(6), 対策を踏まえた更新見込み年度 number(4,0), 対策費用・2020年（千円） number(5,0), 対策内容・2020年 char(21), 対策費用・2021年（千円） number(6,0), 対策内容・2021年 char(21),
      対策費用・2022年（千円） number(6,0), 対策内容・2022年 char(21), 対策費用・2023年（千円） number(6,0), 対策内容・2023年 char(21), 対策費用・2024年（千円） number(6,0), 対策内容・2024年 char(39), 対策費用・2025年（千円） number(6,0), 対策内容・2025年 char(21), 対策費用・2026年（千円） number(6,0), 対策内容・2026年 char(21), 対策費用・2027年（千円） number(6,0), 対策内容・2027年 char(21), 対策費用・2028年（千円） number(5,0), 対策内容・2028年 char(21), 対策費用・2029年（千円） number(6,0), 対策内容・2029年 char(39), 長寿命化に向けた特記事項 char(96)
    -> Tester_2
Tester_2
    BOOL_OP = OR
    TEST_CLAUSE = TEST gml:id ATTRIBUTE_HAS_A_VALUE ""
    TEST_MODE = TEST
    PASSED -> FeatureMerger [SUPPLIER]
FeatureMerger
    ATTR_ACCUM_MODE = Merge Supplier
    ATTR_CONFLICT_RES_LOOKUP = REQUESTOR_IF_CONFLICT
    IGNORE_NULLS = No
    JOIN_KEYS = @Value(gml_parent_id) @Value(gml:id) AUTO
    MERGE_TYPE = Attributes Only
    PROCESS_DUPS = NO
    REJECT_NULL_MISSING_KEYS = No
    SUPPLIERS_FIRST = No
    ATTR_CONFLICT_RES = Use Requestor
    MERGED -> AttributeManager_3
AttributeManager_3
    ATTR_TABLE:
      REMOVE _folder_package (buffer)
      RENAME_SET_VALUE gml_parent_id > gml_id (varchar(200))
      REMOVE gml:id (varchar(41))
    -> trk_attribute (writer CSV2_2)
    -> trk (writer MVT_TILESET_1)
trk (writer MVT_TILESET_1)
    attributes: gml_id string, 公園コード string, 公園名 string, 公園種別 string, 施設コード string, 公園施設種類【選択】 string, 公園施設名【選択】 string, 公園施設名（任意） string, 具体的施設名称 string, 数量（数値） double, 数量（単位【選択】_ string, 規模 string, 主要部材【選択】 string, 主要部材（任意） string, 設置年度 int64, 経過年数 int64, 処分制限期間など int64, 使用見込み期間 int64, 健全度調査以前に実施した補修の有無（有無） string, 健全度調査以前に実施した補修の有無（年度） string, 健全度調査（年度） int64, 健全度調査（劣化状況） string, 健全度調査（健全度） string, 健全度調査（緊急度） string, 管理類型 string, 対策を踏まえた更新見込み年度 int64, 対策費用・2020年（千円） int64, 対策内容・2020年 string, 対策費用・2021年（千円） int64, 対策内容・2021年 string,
      対策費用・2022年（千円） int64, 対策内容・2022年 string, 対策費用・2023年（千円） int64, 対策内容・2023年 string, 対策費用・2024年（千円） int64, 対策内容・2024年 string, 対策費用・2025年（千円） int64, 対策内容・2025年 string, 対策費用・2026年（千円） int64, 対策内容・2026年 string, 対策費用・2027年（千円） int64, 対策内容・2027年 string, 対策費用・2028年（千円） int64, 対策内容・2028年 string, 対策費用・2029年（千円） int64, 対策内容・2029年 string, 長寿命化に向けた特記事項 string
trk_attribute (writer CSV2_2)
    attributes: gml_id varchar(200), 公園コード varchar(3), 公園名 varchar(24), 公園種別 varchar(6), 施設コード varchar(7), 公園施設種類【選択】 varchar(15), 公園施設名【選択】 varchar(21), 公園施設名（任意） varchar(48), 具体的施設名称 varchar(63), 数量（数値） number(7,1), 数量（単位【選択】) varchar(3), 規模 varchar(11), 主要部材【選択】 varchar(18), 主要部材（任意） varchar(39), 設置年度 number(4,0), 経過年数 number(2,0), 処分制限期間など number(2,0), 使用見込み期間 number(2,0), 健全度調査以前に実施した補修の有無（有無） varchar(1), 健全度調査以前に実施した補修の有無（年度） varchar(1), 健全度調査（年度） number(4,0), 健全度調査（劣化状況） varchar(285), 健全度調査（健全度） varchar(3), 健全度調査（緊急度） varchar(3), 管理類型 varchar(6), 対策を踏まえた更新見込み年度 number(4,0), 対策費用・2020年（千円） number(5,0), 対策内容・2020年 varchar(21), 対策費用・2021年（千円） number(6,0), 対策内容・2021年 varchar(21),
      対策費用・2022年（千円） number(6,0), 対策内容・2022年 varchar(21), 対策費用・2023年（千円） number(6,0), 対策内容・2023年 varchar(21), 対策費用・2024年（千円） number(6,0), 対策内容・2024年 varchar(39), 対策費用・2025年（千円） number(6,0), 対策内容・2025年 varchar(21), 対策費用・2026年（千円） number(6,0), 対策内容・2026年 varchar(21), 対策費用・2027年（千円） number(6,0), 対策内容・2027年 varchar(21), 対策費用・2028年（千円） number(5,0), 対策内容・2028年 varchar(21), 対策費用・2029年（千円） number(6,0), 対策内容・2029年 varchar(39), 長寿命化に向けた特記事項 varchar(96)

Bookmark: ファイルごとの最大LOD抽出
StringSearcher
    CASE = no
    MATCHED_RESULT_ATTR = code
    PRESERVE_FEATURE_ORDER_LOOKUP = PER_OUTPUT_PORT
    REGEXP = ^\d+
    STRING_TO_SEARCH = @Value(_gml_filename)
    MATCHED -> StringLengthCalculator
StringLengthCalculator
    LENGTH_ATTR = _length
    SRC_ATTR = _folder_package
    -> AttributeManager_6
AttributeManager_6
    ATTR_TABLE:
      RENAME_SET_VALUE _folder_package > type (buffer)
      RENAME_SET_VALUE _max_lod > maxLod (int16)
      SET_TO _length (uint64) = @Evaluate(@CurrentAttribute()+1)
      SET_TO file (varchar(200)) = @TrimLeft(@Substring(@Value(_udx_dirs),@Value(_length))/@Value(_gml_filename),/)
      REMOVE _folder_root (buffer)
      REMOVE _udx_dirs (buffer)
      REMOVE _gml_path (buffer)
      REMOVE _gml_filename (buffer)
      REMOVE _meshcode (buffer)
      REMOVE _city_code (varchar(200))
      REMOVE _city_name (buffer)
      REMOVE _feature_types (buffer)
    -> maxLod (writer CSV2_1)

Bookmark: フィーチャー選択
Tester_lod2
    BOOL_OP = OR
    TEST_CLAUSE = TEST @Value(feature_type) IN tran:TrafficArea,tran:AuxiliaryTrafficArea
    TEST_MODE = TEST
    PASSED -> 2DForcer_lod0-2
Tester_lod3
    BOOL_OP = OR
    TEST_CLAUSE = TEST @Value(feature_type) IN tran:TrafficArea,tran:AuxiliaryTrafficArea
    TEST_MODE = TEST
    PASSED -> CsmapReprojector_lod3

FME custom transformer TextureInterpretationCoercer

Parameters:
- INTERPRETATION = RGB24   # Destination Interpretation Type
- WAIT_COERCE_COMPLETE = No   # Wait for Coerce to Complete

Input (input)
    -> SharedItemRetriever
    -> Junction_2
Junction_2
    -> Junction_3
Junction_3
    -> Tester_2
Tester_2
    BOOL_OP = OR
    TEST_CLAUSE = TEST $(WAIT_COERCE_COMPLETE) = No
    TEST_MODE = TEST
    PASSED -> Junction_8
    FAILED -> FeatureMerger [REQUESTOR]
Junction_8
    -> Junction_9
Junction_9
    -> Output (output)
SharedItemRetriever
    ACCUM_ATTRS = No
    ACCUM_TRAITS = NO
    ID_SOURCE_LOOKUP = IDUSED
    RECURSIVE = No
    REF_ATTR_STORAGE = _shared_item_id
    SHARED_OBJECT_TYPE = RASTER
    SIDE_OPTION = BOTH
    UNIQUE_DEFINITIONS = YES
    ACCUM_TRAITS_LOOKUP = Drop
    ID_SOURCE = From Geometry Properties
    SHARED_TYPE = Raster
    SIDE_TO_EXTRACT = Front and Back Sides
    UNIQUE_STYLES = No
    -> RasterPropertyExtractor
    <REJECTED> -> Junction
RasterPropertyExtractor
    -> Tester
    <REJECTED> -> Junction_4
Tester
    BOOL_OP = OR
    TEST_CLAUSE = TEST @Value(_num_bands) NOT_IN 3,4
    TEST_MODE = TEST
    PASSED -> RasterInterpretationCoercer
RasterInterpretationCoercer
    COLOR_TO_COLOR_LOOKUP = TYPESCALE
    COLOR_TO_NUMERIC_LOOKUP = BOUNDED_CAST
    FLOAT_TO_INTEGER_LOOKUP = ROUND
    INTERPRETATION_LOOKUP = $(INTERPRETATION)
    NUMERIC_TO_COLOR_LOOKUP = DATASCALE
    NUMERIC_TO_NUMERIC_LOOKUP = BOUNDED_CAST
    RGBA_TO_RGB_LOOKUP = DROPALPHA
    RGB_TO_RGBA_LOOKUP = CREATEOPAQUEALPHA
    COLOR_TO_COLOR = Scale by data type
    COLOR_TO_NUMERIC = Bounded cast
    FLOAT_TO_INTEGER = Round
    INTERPRETATION = $(INTERPRETATION)
    NUMERIC_TO_COLOR = Scale by data values
    NUMERIC_TO_NUMERIC = Bounded cast
    RGBA_TO_RGB = Drop the alpha band
    RGB_TO_RGBA = Create opaque alpha band
    -> SharedItemAdder
    <REJECTED> -> Junction_5
SharedItemAdder
    SHARED_OBJECT_REF = _shared_item_id
    SHARED_OBJ_TYPE = RASTER
    STORAGE = REPLACE
    SHARED_TYPE = Raster
    STORAGE_MODE = Replace Existing Item
    -> Sampler
    <REJECTED> -> Junction_6
Sampler
    MODE = ORIGINAL
    RATE = 1
    SAMPLE_TYPE_MULTIPLIER = 0
    SAMPLE_MODE = No
    SAMPLE_TYPE_LONG = Last N Features
    SAMPLED -> AttributeKeeper
AttributeKeeper
    CREATE_BULK_MODE_FEATURES = NO
    -> FeatureMerger [SUPPLIER]
FeatureMerger
    ATTR_ACCUM_MODE = Merge Supplier
    ATTR_CONFLICT_RES_LOOKUP = REQUESTOR_IF_CONFLICT
    IGNORE_NULLS = No
    JOIN_KEYS = 1 1 AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> Junction_7
    UNMERGED_REQUESTOR -> Junction_7
Junction_7
    -> Output (output)
Output (output)
Junction_6
Junction_5
Junction_4
Junction

FME custom transformer FilePathExtractor
Extracts all the file paths which can be accessed by a string specified through a Filename (Multiple) type user parameter, and outputs features each of which has attributes storing the file path, file name, directory path etc.  
If the source string contains a zip or 7-Zip file path which is specified with the Select Multiple Folders/Files function (called "Advanced Browser" in the old days), the transformer considers it as a folder-like thing, will extact it automatically and output features for each extracted file.  
A zip or a 7z file directly specified with the standard Select Files dialog will also be extracted by default. However, you can set No to the Extract Archives parameter not to extract them.
Parameters
Source Dataset
Extract Archives

Parameters:
- SOURCE_DATASET =   # Source Dataset
- EXTRACT_ARCHIVES = Yes   # Extract Archives

Initiator (input)
    -> ParameterFetcher
ParameterFetcher
    ATTR_LIST = __source_dataset $(SOURCE_DATASET)
    -> PythonCaller
PythonCaller
    HIDE_ATTRIBUTES = __source_dataset
    NEW_ATTRIBUTES = __path_unix
    PYTHONSOURCE:
      import fme
      import fmeobjects
      import shlex
      class PathElementExtractor(object):
          def __init__(self):
              pass

          def input(self, feature):
              dataset = feature.getAttribute('__source_dataset').replace('\\', '/')
              feature.removeAttribute('__source_dataset')
              if dataset.startswith('"'):
                  for path in shlex.split(dataset.replace('""', '"')):
                      feature.setAttribute('__path_unix', path)
                      self.pyoutput(feature)
              else:
                  feature.setAttribute('__path_unix', dataset)
                  self.pyoutput(feature)

          def close(self):
              pass
    PYTHONSYMBOL = PathElementExtractor
    -> StringSearcher
Note: ^(.+\.(zip|7z|7zip))\[(.+)\]$
StringSearcher
    CASE = no
    MATCHED_PARTS_ATTR = _sub
    PRESERVE_FEATURE_ORDER_LOOKUP = PER_OUTPUT_PORT
    REGEXP = ^(.+\.(zip|7z|7zip))\[(.+)\]$
    STRING_TO_SEARCH = @Value(__path_unix)
    MATCHED -> AttributeManager
    NOT_MATCHED -> AttributeCreator
AttributeManager
    ATTR_TABLE:
      SET_TO __dirpath = FME_CONDITIONAL:DEFAULT_VALUE'@Value(_sub{0}.part)'BOOL_OP;OR;COMPOSITE_TEST;1;CASE_INSENSITIVE_TEST @Value(_sub{1}.part) BEGINS_WITH **/'@Value(_sub{0}.part)/**/'FME_NUM_CONDITIONS2___
      SET_TO __recurse_into_subfolders = FME_CONDITIONAL:DEFAULT_VALUE'No'BOOL_OP;OR;COMPOSITE_TEST;1;CASE_INSENSITIVE_TEST @Value(_sub{2}.part) BEGINS_WITH **/'Yes'FME_NUM_CONDITIONS2___
      SET_TO __path_filter = @ReplaceRegEx(@Value(_sub{2}.part),"(\*\*/)?(.+)",\2)
      SET_TO __dirpath = @Value(_sub{0}.part)
      SET_TO
      REMOVE __path_unix
      REMOVE _sub{}.part
      REMOVE _sub{}.startIndex
    -> FeatureReader [INITIATOR]
AttributeCreator
    ATTR_TABLE = SET_TO __recurse_into_subfolders = No
    -> FilenamePartExtractor
FilenamePartExtractor
    DIRPATH_ATTR = __dirpath
    FULLNAME_ATTR = __path_filter
    SRC_ATTR = @Value(__path_unix)
    -> FeatureReader [INITIATOR]
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Merge Initiator and Result
    ATTR_CONFLICT_RES = Use Result
    COMBINE_GEOM = Use Initiator
    DATASET = @Value(__dirpath)
    FORMAT = PATH
    OUTPUT_FEATURES_DISPLAY = Data Features
    PATH_GLOB_PATTERN = @Value(__path_filter)
    PATH_NO_EMPTY_PROPERTIES = YES
    PATH_RECURSE_DIRECTORIES = @Value(__recurse_into_subfolders)
    PATH_RETRIEVE_FILE_PROPERTIES = NO
    PATH_TYPE = FILE
    PATH -> Tester
Tester
    BOOL_OP = COMPOSITE
    COMPOSITE_TEST = 1 AND 2
    TEST_CLAUSE:
      CASE_INSENSITIVE_TEST @Value(path_extension) IN zip,7z,7zip
      CASE_INSENSITIVE_TEST $(EXTRACT_ARCHIVES) = Yes
    TEST_MODE = CASE_INSENSITIVE_TEST
    PASSED -> FeatureReader_2 [INITIATOR]
    FAILED -> AttributeManager_2
Note: Extract archives.
FeatureReader_2
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Merge Initiator and Result
    ATTR_CONFLICT_RES = Use Result
    COMBINE_GEOM = Use Initiator
    DATASET = @Value(path_unix)
    FORMAT = PATH
    OUTPUT_FEATURES_DISPLAY = Data Features
    PATH_GLOB_PATTERN = *
    PATH_NO_EMPTY_PROPERTIES = YES
    PATH_RECURSE_DIRECTORIES = YES
    PATH_RETRIEVE_FILE_PROPERTIES = NO
    PATH_TYPE = FILE
    PATH -> AttributeManager_2
AttributeManager_2
    ATTR_TABLE:
      RENAME_SET_VALUE path_unix > _path_unix
      RENAME_SET_VALUE path_windows > _path_windows
      RENAME_SET_VALUE path_filename > _path_filename
      RENAME_SET_VALUE path_rootname > _path_rootname
      RENAME_SET_VALUE path_extension > _path_extension
      RENAME_SET_VALUE path_directory_unix > _path_directory_unix
      RENAME_SET_VALUE path_directory_windows > _path_directory_windows
      REMOVE __path_unix
      REMOVE __dirpath
      REMOVE __path_filter
      REMOVE path_filesize
      REMOVE path_ownername
      REMOVE path_readonly
      REMOVE path_modified_date
      REMOVE path_created_date
      REMOVE path_accessed_date
      REMOVE path_type
      REMOVE fme_geometry{}
      REMOVE __recurse_into_subfolders
      REMOVE fme_geometry{0}
    -> Output (output)
Output (output)

FME custom transformer SchemaDefinitionSetter

Parameters:
- TARGET_PACKAGE =   # Target Package (trn, rwy, trk, squr, wwy)
- SCHEMA_DEFS_SON = {}   # Schema Definition JSON

Input (input)
    -> ParameterFetcher
ParameterFetcher
    ATTR_LIST = __package $(TARGET_PACKAGE) __schema_defs $(SCHEMA_DEFS_SON)
    -> PythonCaller
PythonCaller
    PYTHONSOURCE:
      import fme
      import fmeobjects, json

      class SchemaDefinitionSetter(object):
          def __init__(self):
              self.flattenAttrs = None # {feature type : schema definition}
              self.featureTypes = set([])

          def input(self, feature):
              if self.flattenAttrs == None:
                  self.flattenAttrs = json.loads(feature.getAttribute('__schema_defs'))

              ftype = feature.getAttribute('__package')
              if ftype not in self.featureTypes:
                  self.featureTypes.add(ftype)

                  schema = [
                      # 全パッケージ共通属性
                      ('meshcode', 'fme_varchar(16)'),
                      ('feature_type', 'fme_buffer'),
                      ('city_code', 'fme_varchar(8)'),
                      ('city_name', 'fme_varchar(64)'),
                      ('gml_id', 'fme_varchar(64)'),
                      ('attributes', 'fme_json'),
                  ]

                  # フラットにする属性のスキーマ定義を追加
                  schemaDefs = self.flattenAttrs.get(ftype, [])
                  for obj in schemaDefs:
                      name = obj['attribute']
                      type = 'fme_' + obj['data_type']
                      schema.append((name, type))

                  # スキーマ定義属性を設定
                  for i, (name, type) in enumerate(schema):
                      prefix = 'attribute{%d}' % i
                      feature.setAttribute(prefix + '.name', name)
                      feature.setAttribute(prefix + '.fme_data_type', type)

              self.pyoutput(feature)

          def process_group(self):
              pass

          def close(self):
              pass

          def has_support_for(self, support_type):
              if support_type == fmeobjects.FME_SUPPORT_FEATURE_TABLE_SHIM:
                  return False
              return False
    PYTHONSYMBOL = SchemaDefinitionSetter
    -> AttributeRemover
AttributeRemover
    REMOVE_ATTRS = __package,__schema_defs
    -> Output (output)
Output (output)

FME custom transformer PLATEAU4.AttributeReader_v2

Parameters:
- DATA_FILE =   # 3D都市モデルデータセット
- CITY_CODE =   # 市区町村コード (5桁数字)
- DICT_OF_ATTRS_TO_FLAT = {}   # フラット化属性 {接頭辞/地物型 : [ { 属性名, JSONパス, データ型 } ] }
- GRP_OPTIONS =   # オプション
- STD_SPEC_VERSION = 4   # PLATEAU 標準製品仕様書の版番号
- TARGET_PACKAGES =   # 対象とするパッケージ
- CODELISTS_FOLDER =   # codelists フォルダー
- SCHEMAS_FOLDER =   # schemas フォルダー
- ADD_NSPREFIX_TO_FEATURE_TYPES = Yes   # フィーチャータイプ名リストに _ 区切り名前空間プレフィクスをつける

Initiator (input)
    -> PLATEAU4.FolderAndFilePathReader [Initiator]
PLATEAU4.FolderAndFilePathReader
    CODELISTS_FOLDER = $(CODELISTS_FOLDER)
    DATA_FILE = $(DATA_FILE)
    SCHEMAS_FOLDER = $(SCHEMAS_FOLDER)
    TARGET_PACKAGES = $(TARGET_PACKAGES)
    Matched -> XMLFragmenter
Note: cityObjectMember/* / BuildingPart / BridgePart / TunnelPart / TrafficArea / AuxiliaryTrafficArea
XMLFragmenter
    DISABLE_EXTERNAL_ENTITY_PROCESSING = Yes
    EMBEDDED_EXPRESSIONS = cityObjectMember/* BuildingPart BridgePart TunnelPart TrafficArea AuxiliaryTrafficArea
    ENTITY_RESOLVER = Yes
    FEATURE_TYPES_FORMAT_NAME = XML
    FILE_XML = @Value(_gml_path)
    IGNORE_DATASET_EXTERNAL_DTD = No
    MERGE_ATTRS = Yes
    REJECT_FEATURES_WITH_NO_FRAGMENTS = NO
    XML_SOURCE_TYPE = xml_file
    FRAGMENTS -> AttributeManager
Note: 不要な属性削除 / メッシュコード (ファイル名先頭要素) 抽出
AttributeManager
    ATTR_TABLE:
      REMOVE _folder_admin (buffer)
      REMOVE _folder_area (buffer)
      REMOVE _dir_root (buffer)
      SET_TO _meshcode (varchar(200)) = @ReplaceRegularExpression(@Value(_gml_filename),^(.+?)_.+$,\1,caseSensitive=TRUE)
      REMOVE _file_index (int64)
      REMOVE xml_parent_child_pos (uint32)
      SET_TO __add_nsprefix_to_feature_types (varchar(200)) = $(ADD_NSPREFIX_TO_FEATURE_TYPES)
      SET_TO __std_spec_version (varchar(200)) = $(STD_SPEC_VERSION)
      SET_TO _city_code (varchar(200)) = $(CITY_CODE)
      SET_TO _dict_of_attrs_to_flat (varchar(200)) = $(DICT_OF_ATTRS_TO_FLAT)
    USER_EXPOSED_ATTRIBUTES = _feature_types,_feature_types_with_prefix,_feature_types_without_prefix
    -> PythonCaller
Note: 主題属性を抽出してJSON文書に集約 / 一部属性のフラット化
PythonCaller
    GROUP_BY = _gml_path
    NEW_ATTRIBUTES = _city_name buffer _feature_type buffer gml_id buffer _attributes json _num_lod0 int16 _num_lod1 int16 _num_lod2 int16 _num_lod3 int16 _num_lod4 int16 _max_lod int16 _num_files int64 _num_features int64 _codelists json __is_filepath buffer __is_summary buffer _feature_types buffer _flatten_attrs json __is_schema buffer
    PYTHONSOURCE:
      import fme
      import fmeobjects, os, json, re
      import xml.etree.ElementTree as ET

      # 行政区域コードリスト名
      kAdminCodeList = 'Common_localPublicAuthorities.xml'

      # XML名前空間 {プレフィクス : 名前空間名} 辞書
      XMLNS = {
          "app" : "http://www.opengis.net/citygml/appearance/2.0",
          "bldg" : "http://www.opengis.net/citygml/building/2.0",
          "brid" : "http://www.opengis.net/citygml/bridge/2.0",
          "core" : "http://www.opengis.net/citygml/2.0",
          "dem" : "http://www.opengis.net/citygml/relief/2.0",
          "frn" : "http://www.opengis.net/citygml/cityfurniture/2.0",
          "gen" : "http://www.opengis.net/citygml/generics/2.0",
          "gml" : "http://www.opengis.net/gml",
          "grp" : "http://www.opengis.net/citygml/cityobjectgroup/2.0",
          "luse" : "http://www.opengis.net/citygml/landuse/2.0",
          "pbase" : "http://www.opengis.net/citygml/profiles/base/2.0",
          "sch" : "http://www.ascc.net/xml/schematron",
          "smil20" : "http://www.w3.org/2001/SMIL20/",
          "smil20lang" : "http://www.w3.org/2001/SMIL20/Language",
          "tex" : "http://www.opengis.net/citygml/texturedsurface/2.0",
          "tran" : "http://www.opengis.net/citygml/transportation/2.0",
          "tun" : "http://www.opengis.net/citygml/tunnel/2.0",
          "veg" : "http://www.opengis.net/citygml/vegetation/2.0",
          "wtr" : "http://www.opengis.net/citygml/waterbody/2.0",
          "xAL" : "urn:oasis:names:tc:ciq:xsdschema:xAL:2.0",
          "xlink" : "http://www.w3.org/1999/xlink",
          "xsi" : "http://www.w3.org/2001/XMLSchema-instance",
      }

      # 汎用属性タグとタイプ名
      GEN_ATTR_TYPES = {
          'gen:stringAttribute' : 'string',
          'gen:intAttribute' : 'int',
          'gen:doubleAttribute' : 'double',
          'gen:dateAttribute' : 'date',
          'gen:uriAttribute' : 'uri',
          'gen:measureAttribute' : 'measure',
          'gen:genericAttributeSet' : 'attributeSet',
      }

      # 数値として評価できる値だが文字列として取り扱う要素タグ
      NON_NUMERIC_TAGS = {
          'uro:lodType',
      }

      # BuildingPartなどの部分フィーチャータイプ
      PART_FEATURE_TYPES = {
          'bldg:BuildingPart',
          'brid:BridgePart',
          'tun:TunnelPart',
      }

      # 交通領域、補助交通領域フィーチャータイプ
      TRAFFIC_AREA_FEATURE_TYPES = {
          'tran:TrafficArea',
          'tran:AuxiliaryTrafficArea',
      }

      # スキップするXML要素
      SKIPPABLE_TAGS = {
          'bldg:boundedBy',
          'bldg:opening',
          'bldg:interiorRoom',
          'bldg:interiorFurniture',
          'bldg:outerBuildingInstallation',
          'bldg:interiorBuildingInstallation',
          'bldg:roomInstallation',
          'bldg:consistsOfBuildingPart',
          'brid:boundedBy',
          'brid:opening',
          'brid:interiorBridgeRoom',
          'brid:interiorFurniture',
          'brid:outerBridgeInstallation',
          'brid:interiorBridgeInstallation',
          'brid:bridgeRoomInstallation',
          'brid:consistsOfBridgePart',
          'tun:boundedBy',
          'tun:opening',
          'tun:interiorHollowSpace',
          'tun:interiorFurniture',
          'tun:outerTunnelInstallation',
          'tun:interiorTunnelInstallation',
          'tun:hollowSpaceInstallation',
          'tun:consistsOfTunnelPart',
          'tran:trafficArea',
          'tran:auxiliaryTrafficArea',
          'wtr:boundedBy',
      }

      class AttributeReader(object):
          def __init__(self):
              self.codelists = {} # {コードリストファイルパス : {コード : 意味文字列}}
              self.codeListsDir = None # コードリスト保存先(codelistsフォルダー）のパス
              self.cityCodeToName = {} # {市区町村コード : 市区町村名}
              self.xmlnsToPrefix = {} # {名前空間フルネーム : 名前空間修飾子}
              self.stdSpecVersion = 0 # 標準製品仕様書のメジャーバージョン
              self.curDir = os.getcwd() # カレントディレクトリを取得（closeメソッドで元に戻す）
              self.dataDir = None

              self.dictOfAttrsToFlat = None # フラットにする属性定義辞書
              self.maxLod = 0 # 最大LOD全フィーチャー処理後に更新して Summary フィーチャーに与える。
              self.fileCount = 0 # ファイル数カウンター
              self.featureCount = 0 # フィーチャー数カウンター
              self.logger = fmeobjects.FMELogFile()

              pattern = re.compile(r'.+:lod[0-4].+')
              self.isLodTag = lambda tag : bool(pattern.match(tag))

              self.init_group()

          # グループ (ファイルパス) ごとの初期化処理
          def init_group(self):
              self.numLod = [0 for i in range(5)] # LOD別フィーチャー数カウント。フィーチャー読込後に更新する。
              self.firstFeature = None
              self.features = []
              self.xidToFeature = {} # {xml_id : feature}
              self.partFeatures = set([]) # BuildingPart等の部分フィーチャー
              self.trafficAreaFeatures = set([]) # 道路等の交通領域, 補助交通領域
              self.subFeatures = set([]) # 下位地物型 (RoofSurface等) のフィーチャー (LOD4)
              self.featureTypes = set([]) # 読み込まれたフィーチャータイプ名

          # XML名前空間 {プレフィクス : 名前空間名} 辞書更新
          def update_xmlns_dictionary(self, feature):
              ver = int(feature.getAttribute('__std_spec_version'))
              if ver != self.stdSpecVersion:
                  if ver == 2:
                      XMLNS.update({
                          "uro" : "https://www.geospatial.jp/iur/uro/2.0",
                          "urf" : "https://www.geospatial.jp/iur/urf/2.0",
                      })
                  elif ver == 3:
                      XMLNS.update({
                          "uro" : "https://www.geospatial.jp/iur/uro/3.0",
                          "urf" : "https://www.geospatial.jp/iur/urf/3.0",
                      })
                  elif ver == 4:
                      XMLNS.update({
                          "uro" : "https://www.geospatial.jp/iur/uro/3.1",
                          "urf" : "https://www.geospatial.jp/iur/urf/3.1",
                      })
                  else:
                      raise Exception('Unexpected version of PLATEAU Standard Specifications')

                  for prefix, namespace in XMLNS.items():
                      ET.register_namespace(prefix, namespace)

                  self.xmlnsToPrefix = {n : p for p, n in XMLNS.items()} # {名前空間 : プレフィクス}
                  self.stdSpecVersion = ver

          # コードリスト辞書更新
          def update_codelists(self, feature):
              dir = os.path.abspath(feature.getAttribute('_dir_codelists'))
              if dir != self.codeListsDir:
                  if os.path.exists(dir) and os.path.isdir(dir):
                      for f in os.listdir(dir):
                          path = os.path.join(dir, f).replace('\\', '/')
                          if os.path.isfile(path) and path.endswith('.xml'):
                              try:
                                  gmlns = {'gml' : 'http://www.opengis.net/gml'}
                                  rt = ET.parse(path).getroot()
                                  codelist = {
                                      d.find('gml:name', gmlns).text : d.find('gml:description', gmlns).text
                                      for d in rt.findall('.//gml:Definition', gmlns)
                                  }
                                  self.codelists[path] = codelist
                                  if f == kAdminCodeList: # 市区町村コード:市区町村名辞書取得
                                      self.cityCodeToName = codelist
                              except Exception as ex:
                                  pass
                      self.codeListsDir = dir

          # XMLタグに含まれれる"{名前空間名}"をプレフィクス"xxx:"に置換
          def replace_namespace_with_prefix(self, tag):
              m = re.match(r'^\{(.+)\}(.+)', tag)
              if m is not None and m.group(1) in self.xmlnsToPrefix:
                  return '%s:%s' % (self.xmlnsToPrefix[m.group(1)], m.group(2))
              else:
                  return None

          # 汎用属性,汎用属性セットから属性を抽出して属性辞書 (attrib) に追加
          def add_generic_attributes(self, attrib, key, node):
              try:
                  tag = self.replace_namespace_with_prefix(node.tag)
                  type = GEN_ATTR_TYPES.get(tag, 'unknown')
                  if tag == 'gen:genericAttributeSet':
                      attrSet = {}
                      for child in node.findall('./*'):
                          self.add_generic_attributes(attrSet, key, child)
                      if attrSet:
                          attr = {
                              'type' : type,
                              'name' : node.get('name'),
                              'value' : attrSet[key],
                          }
                          attrib.setdefault(key, []).append(attr)
                  else:
                      v = node.find('./gen:value', XMLNS)
                      attr = {
                          'type' : type,
                          'name' : node.get('name'),
                          'value' : float(v.text) if type in ['int', 'double', 'measure'] else v.text,
                      }
                      if type == 'measure':
                          attr['uom'] = v.get('uom')
                      attrib.setdefault(key, []).append(attr)
              except Exception as ex:
                  print(ex)

          # core:AddressPropertyType 型の属性（住所）抽出
          def get_address(self, node):
              s = []
              for x in node.findall('.//xAL:LocalityName', XMLNS):
                  if x.text:
                      s.append(x.text)
              for d in node.findall('.//xAL:DependentLocality', XMLNS):
                  t = d.get('Type')
                  if t and t == 'district':
                      for x in d.findall('./*', XMLNS):
                          if x.text:
                              s.append(x.text)
                      break
              return ''.join(s)

          # 主題属性の値の抽出
          def get_node_value(self, attrib, node, tag):
              text = node.text.strip() if node.text is not None else ''
              if text != '':
                  codeSpace = node.get('codeSpace', None) # codeSpace 属性
                  if codeSpace is not None:
                      k = os.path.abspath(codeSpace).replace('\\', '/')
                      d = self.codelists.get(k, None)
                      value = d.get(text, text) if d is not None else text
                      attrib.setdefault(tag, []).append(value)
                      attrib.setdefault(tag + '_code', []).append(text)

                  elif tag in NON_NUMERIC_TAGS:
                      attrib.setdefault(tag, []).append(text)

                  else:
                      try:
                          num = int(text)
                          value = text if (1 < len(text) and text[0] == '0') else num
                      except:
                          try:
                              value = float(text)
                          except:
                              value = text

                      attrib.setdefault(tag, []).append(value)
                      uom = node.get('uom', None) # uom属性
                      if uom is not None:
                          attrib.setdefault(tag + '_uom', []).append(uom)

          # parent要素以下の主題属性を収集してJSON辞書 (attrib) に追加
          def collect_attributes(self, attrib, parent, num_lods):
              keyToValues = {} # {key : [values]}
              for node in parent.findall('./*'):
                  tag = self.replace_namespace_with_prefix(node.tag)
                  if tag == None or tag in SKIPPABLE_TAGS:
                      pass

                  elif tag == 'bldg:address':
                      keyToValues.setdefault(tag, []).append(self.get_address(node))

                  elif tag in GEN_ATTR_TYPES:
                      kv = {}
                      key = 'gen:genericAttribute'
                      self.add_generic_attributes(kv, key, node)
                      keyToValues.setdefault(key, []).append(kv[key][0])

                  elif len(list(node)) == 0:
                      self.get_node_value(keyToValues, node, tag)

                  elif self.isLodTag(tag):
                      m = re.match(r'.+:lod(\d).+', tag)
                      lod = int(m.group(1))
                      num_lods[lod] += 1
                      self.numLod[lod] += 1

                  else:
                      child = node[0]
                      if tag == 'uro:parameter': # 鉄道モデル uro:ControlPoint/uro:parameter
                          if 0 < len(list(child)):
                              child = child[0]
                          else:
                              continue
                      tag = self.replace_namespace_with_prefix(child.tag)
                      kv = {}
                      self.collect_attributes(kv, child, num_lods) # recursive function call
                      if 0 < len(kv):
                          keyToValues.setdefault(tag, []).append(kv)

              for key, values in keyToValues.items():
                  if len(values) == 1 and not isinstance(values[0], dict):
                      keyToValues[key] = values[0]
              attrib.update(keyToValues)

          def input(self, feature):
              # フラットにする主題属性辞書初期化
              if self.dictOfAttrsToFlat == None:
                  self.dictOfAttrsToFlat = json.loads(feature.getAttribute('_dict_of_attrs_to_flat'))

              # ファイルごとの最初のフィーチャー
              if self.firstFeature == None:
                  self.firstFeature = feature

              # XML名前空間辞書更新
              self.update_xmlns_dictionary(feature)

              # コードリスト辞書更新
              self.update_codelists(feature)

              # データ内に相対パスで記述されているコードリストファイルパスの絶対パスを取得するため、
              # カレントディレクトリを入力データファイルが保存されている場所にする。
              gmlPath = feature.getAttribute('_gml_path')
              newDir, _ = os.path.split(gmlPath)
              if newDir != self.dataDir:
                  os.chdir(newDir)

              # XMLツリー作成, gml:id取得。gml:id が定義されていなければスキップ。
              root = ET.fromstring(feature.getAttribute('xml_fragment'))
              gml_id = root.get("{http://www.opengis.net/gml}id")
              if gml_id is None:
                  return

              mcode = feature.getAttribute('_meshcode')
              ftype = self.replace_namespace_with_prefix(root.tag)
              self.featureTypes.add(ftype)

              # 全属性を集約するJSON文書
              attrib = {
                  "meshcode" : mcode,
                  "feature_type" : ftype,
                  "gml:id" : gml_id,
              }

              # 主題属性を抽出, JSON文書に集約
              # LOD別空間属性要素数カウント
              num_lods = [0,0,0,0,0]
              self.collect_attributes(attrib, root, num_lods)

              city_code = str(feature.getAttribute('_city_code'))
              is_sub_feature = True if feature.getAttribute('__is_sub_feature') == 'Yes' else False
              featureAttrs = {
                  '_city_name' : self.cityCodeToName.get(city_code, ''),
                  '_feature_type' : ftype,
                  'gml_id' : gml_id,
                  '_attributes' : json.dumps(attrib, ensure_ascii=False),
                  '_num_lod0' : num_lods[0],
                  '_num_lod1' : num_lods[1],
                  '_num_lod2' : num_lods[2],
                  '_num_lod3' : num_lods[3],
                  '_num_lod4' : num_lods[4],
              }
              for name, value in featureAttrs.items():
                  feature.setAttribute(name, value)

              self.features.append(feature)
              self.xidToFeature[feature.getAttribute('xml_id')] = feature
              if ftype in PART_FEATURE_TYPES:
                  self.partFeatures.add(feature)
              elif ftype in TRAFFIC_AREA_FEATURE_TYPES:
                  self.trafficAreaFeatures.add(feature)
              elif is_sub_feature:
                  self.subFeatures.add(feature)

              self.featureCount += 1
              if self.featureCount % 1000 == 0:
                  self.log_feature_count()

          def log_feature_count(self):
              message = 'PLATEAU4.AttributeReader: #%d features have been processed...' % self.featureCount
              self.logger.logMessageString(message)

          def process_group(self):
              if self.fileCount == 0:
                  schema = fmeobjects.FMEFeature()
                  attrib = {
                      '_flatten_attrs' : json.dumps(self.dictOfAttrsToFlat, ensure_ascii=False),
                      '_codelists' : json.dumps(self.codelists, ensure_ascii=False),
                      '__is_schema' : 'Yes',
                  }
                  for name, value in attrib.items():
                      schema.setAttribute(name, value)
                  self.pyoutput(schema)

              self.fileCount += 1

              def collect_ancestor_attributes(child, attrsList):
                  parent = self.xidToFeature.get(child.getAttribute('xml_parent_id'), None)
                  if parent is not None:
                      collect_ancestor_attributes(parent, attrsList)
                      parentAttrs = json.loads(parent.getAttribute('_attributes'))
                      if 'ancestors' in parentAttrs:
                          del parentAttrs['ancestors']
                      attrsList.append(parentAttrs)

              for child in self.partFeatures|self.trafficAreaFeatures|self.subFeatures:
                  attrsList = []
                  collect_ancestor_attributes(child, attrsList)

                  if 0 < len(attrsList):
                      childAttrs = json.loads(child.getAttribute('_attributes'))
                      childAttrs['ancestors'] = attrsList

                      # 部分フィーチャーには、それが持っていない親フィーチャー属性を追加しておく。
                      if child in self.partFeatures:
                          childKeys = set(childAttrs.keys()).copy()
                          for key, value in attrsList[0].items():
                              if key not in childKeys:
                                  childAttrs[key] = value

                      # 建築物は市区町村コードをID属性から取得する必要があるので、下位要素にも追加しておく。
                      elif child in self.subFeatures \
                          and attrsList[0].get('_feature_type', '') in {'bldg:Building', 'bldg:BuildingPart'}:
                              childAttrs['uro:BuildingIDAttribute'] = ancestors[0].get('uro:BuildingIDAttribute', {})

                      child.setAttribute('_attributes', json.dumps(childAttrs, ensure_ascii=False))

              for feature in self.features:
                  # フラットにする主題属性抽出
                  attributes = json.loads(feature.getAttribute('_attributes'))
                  ftype = feature.getAttribute('_feature_type')
                  prefix = feature.getAttribute('_folder_package')
                  attrsList = self.dictOfAttrsToFlat.get('%s/%s' % (prefix, ftype), [])
                  attrib = {}
                  for name, jpath in [(e['attribute'], e['json_path']) for e in attrsList]:
                      d = attributes
                      for key in jpath.split():
                          value = d.get(key, None)
                          if value is None:
                              break
                          if isinstance(value, list):
                              if not isinstance(value[0], dict):
                                  value = ','.join(value) if key == 'uro:lodType' else value[0]
                              else:
                                  d = value[0]
                                  continue
                          if value not in {9999, -9999}:
                              attrib[name] = value
                  for name, value in attrib.items():
                      feature.setAttribute(name, value)

                  # 主題属性フィーチャー出力
                  self.pyoutput(feature)

              # ファイル単位の最大LOD抽出
              max_lod = 0
              for i in range(4, 0, -1):
                  if 0 < self.numLod[i]:
                      max_lod = i
                      break

              # パッケージ単位の最大LOD更新
              if self.maxLod < max_lod:
                  self.maxLod = max_lod

              # FilePathフィーチャー作成, 出力
              if self.firstFeature is not None:
                  feature = self.firstFeature
                  featureTypes = []
                  if feature.getAttribute('__add_nsprefix_to_feature_types') == 'Yes':
                      featureTypes = [t.replace(':', '_') for t in self.featureTypes]
                  else:
                      featureTypes = [t.split(':')[1] for t in self.featureTypes]

                  attrib = {
                      '_max_lod' : max_lod,
                      '_feature_types' : ' '.join(featureTypes),
                      '__is_filepath' : 'Yes',
                  }
                  for name, value in attrib.items():
                      feature.setAttribute(name, value)
                  self.pyoutput(feature)

                  fname = feature.getAttribute('_gml_filename')
                  message = "PLATEAU4.AttributeReader: '%s' has been processed." % fname
                  self.logger.logMessageString(message)

              self.init_group()

          def close(self):
              if self.featureCount % 1000 != 0:
                  self.log_feature_count()

              # Symmary フィーチャー作成、出力
              feature = fmeobjects.FMEFeature()
              attrib = {
                  '_num_files' : self.fileCount,
                  '_num_features' : self.featureCount,
                  '_max_lod' : self.maxLod,
                  '__is_summary' : 'Yes',
              }
              for name, value in attrib.items():
                  feature.setAttribute(name, value)
              self.pyoutput(feature)

              # カレントディレクトリを復元
              os.chdir(self.curDir)

          def has_support_for(self, support_type):
              if support_type == fmeobjects.FME_SUPPORT_FEATURE_TABLE_SHIM:
                  return False
              return False
    PYTHONSYMBOL = AttributeReader
    -> TestFilter
    -> Tester
Note: LOD4の空間属性要素を含むフィーチャー選択
Tester
    BOOL_OP = OR
    TEST_CLAUSE = TEST 0 < @Value(_num_lod4)
    TEST_MODE = TEST
    PASSED -> Junction_4
Note: AttributeManager_2 : Input
Junction_4
    -> Junction_5
Note: Tester : Passed
Junction_5
    -> AttributeManager_2
Note: Rename / xml_id -> _root_xml_id
AttributeManager_2
    ATTR_TABLE:
      RENAME_SET_VALUE xml_id > _root_xml_id (uint32)
      REMOVE xml_matched_element (buffer)
      REMOVE xml_parent_id (uint32)
      REMOVE _num_lod0 (int64)
      REMOVE _num_lod1 (int64)
      REMOVE _num_lod2 (int64)
      REMOVE _num_lod3 (int64)
      REMOVE _num_lod4 (buffer)
    USER_EXPOSED_ATTRIBUTES = xml_parent_child_pos
    -> Counter
Note: xml_id をユニークにするためのサフィクス
Counter
    CNT_ATTR = _suffix
    GROUP_BY = _gml_path
    SCOPE = Local
    START = 0
    -> XMLFragmenter_LOD4
Note: 下位のフィーチャー要素を抽出
Note: boundedBy/* / opening/* / interiorRoom/* / interiorFurniture/* / outerBuildingInstallation/* / interiorBuildingInstallation/* / roomInstallation/* / interiorBridgeRoom/* / outerBridgeInstallation/* / interiorBridgeInstallation/* / bridgeRoomInstallation/* / interiorHollowSpace/* / outerTunnelInstallation/* / interiorTunnelInstallation/* / hollowSpaceInstallation/*
XMLFragmenter_LOD4
    ATTRIBUTE_XML = xml_fragment
    DISABLE_EXTERNAL_ENTITY_PROCESSING = Yes
    EMBEDDED_EXPRESSIONS = boundedBy/* opening/* interiorRoom/* interiorFurniture/* outerBuildingInstallation/* interiorBuildingInstallation/* roomInstallation/* interiorBridgeRoom/* outerBridgeInstallation/* interiorBridgeInstallation/* bridgeRoomInstallation/* interiorHollowSpace/* outerTunnelInstallation/* interiorTunnelInstallation/* hollowSpaceInstallation/*
    ENTITY_RESOLVER = Yes
    FEATURE_TYPES_FORMAT_NAME = XML
    IGNORE_DATASET_EXTERNAL_DTD = No
    MERGE_ATTRS = Yes
    REJECT_FEATURES_WITH_NO_FRAGMENTS = NO
    XML_SOURCE_TYPE = xml_attr
    FRAGMENTS -> XMLXQueryExtractor_LOD4
Note: LOD4の空間属性要素数カウント
XMLXQueryExtractor_LOD4
    QUERY_EXPR = count(//*[starts-with(local-name(), 'lod4')])
    RESULT_ATTRIBUTE = _num_lod4
    RESULT_TYPE = STRING
    WRITE_XML_HEADER = No
    XML_ATTR = xml_fragment
    XML_REMOVE_SOURCE_ATTR = No
    XML_TYPE = xml_attr
    XQUERY_TYPE = xquery_expression
    QUERY_RESULTS -> Tester_2
Note: LOD4の空間属性があるフィーチャーを抽出
Tester_2
    BOOL_OP = OR
    TEST_CLAUSE = TEST 0 < @Value(_num_lod4)
    TEST_MODE = TEST
    PASSED -> AttributeManager_3
Note: Rename / _root_xml_id -> xml_parent_id if Empty / Set Value / xml_id = xm_id_{suffix} / xml_parent_id = xml_parent_id_{suffix} if Not Empty
Note: 読み込みをスキップする下位フィーチャーの関連役割要素 / bldg:boundedBy / bldg:opening / bldg:interiorRoom / bldg:interiorFurniture / bldg:outerBuildingInstallation / bldg:interiorBuildingInstallation / bldg:roomInstallation / bldg:consistsOfBuildingPart / brid:boundedBy / brid:opening / brid:interiorBridgeRoom / brid:interiorFurniture / brid:outerBridgeInstallation / brid:interiorBridgeInstallation / brid:bridgeRoomInstallation / brid:consistsOfBridgePart / tun:boundedBy / tun:opening / tun:interiorHollowSpace / tun:interiorFurniture / tun:outerTunnelInstallation / tun:interiorTunnelInstallation / tun:hollowSpaceInstallation / tun:consistsOfTunnelPart / tran:trafficArea / tran:auxiliaryTrafficArea / wtr:boundedBy
AttributeManager_3
    ATTR_TABLE:
      SET_TO xml_id (uint32) = @CurrentAttribute()_@Value(_suffix)
      SET_TO xml_parent_id (uint32) = FME_CONDITIONAL:DEFAULT_VALUE'@Value(_root_xml_id)'BOOL_OP;OR;COMPOSITE_TEST;1;TEST xml_parent_id ATTRIBUTE_HAS_A_VALUE _FME_BLANK_STRING_'@Value(xml_parent_id)_@Value(_suffix)'FME_NUM_CONDITIONS2___
      SET_TO __is_sub_feature (varchar(3)) = Yes
      REMOVE xml_parent_child_pos (uint32)
      REMOVE _root_xml_id (uint32)
      REMOVE _suffix (int64)
    -> PythonCaller_2
Note: 主題属性を抽出してJSON文書に集約 / 一部属性のフラット化
PythonCaller_2
    GROUP_BY = _gml_path
    NEW_ATTRIBUTES = _city_name buffer _feature_type buffer gml_id buffer _attributes json _num_lod0 int16 _num_lod1 int16 _num_lod2 int16 _num_lod3 int16 _num_lod4 int16 _max_lod int16 _num_files int64 _num_features int64 _codelists json __is_filepath buffer __is_summary buffer _feature_types buffer _flatten_attrs json __is_schema buffer
    PYTHONSYMBOL = AttributeReader
    -> Tester_3
Tester_3
    BOOL_OP = AND
    TEST_CLAUSE:
      TEST __is_summary NOT_ATTRIBUTE_HAS_A_VALUE ""
      TEST __is_filepath NOT_ATTRIBUTE_HAS_A_VALUE ""
      TEST __is_schema NOT_ATTRIBUTE_HAS_A_VALUE ""
    TEST_MODE = TEST
    PASSED -> TestFilter
TestFilter
    DEFAULT_VALUE = AttributeFeature
    PASSED_TEST_GROUP_OUTPUT = FIRST
    TEST_LIST = "BOOL_OP,OR,COMPOSITE_TEST,""""""1"""""",TEST_CLAUSE,TEST __is_summary ATTRIBUTE_HAS_A_VALUE """,Summary,"BOOL_OP,OR,COMPOSITE_TEST,""""""1"""""",TEST_CLAUSE,TEST __is_filepath ATTRIBUTE_HAS_A_VALUE """,FilePath,"BOOL_OP,OR,COMPOSITE_TEST,""""""1"""""",TEST_CLAUSE,TEST __is_schema ATTRIBUTE_HAS_A_VALUE """,Schema
    Summary -> AttributeManager_Summary
    FilePath -> AttributeManager_FilePath
    Schema -> AttributeManager_Schema
    AttributeFeature -> AttributeManager_Feature
AttributeManager_Summary
    ATTR_TABLE:
      REMOVE _codelists (json)
      REMOVE _folder_root (buffer)
      REMOVE _folder_package (buffer)
      REMOVE _udx_dirs (buffer)
      REMOVE _dir_codelists (buffer)
      REMOVE _dir_schemas (buffer)
      REMOVE _gml_path (buffer)
      REMOVE _gml_filename (buffer)
      REMOVE _meshcode (varchar(200))
      REMOVE xml_matched_element (buffer)
      REMOVE xml_fragment (buffer)
      REMOVE xml_id (uint32)
      REMOVE xml_parent_id (uint32)
      REMOVE _num_lod0 (int64)
      REMOVE _num_lod1 (int64)
      REMOVE _num_lod2 (int64)
      REMOVE _num_lod3 (int64)
      REMOVE _num_lod4 (int64)
      REMOVE __add_nsprefix_to_feature_types (varchar(200))
      REMOVE __std_spec_version (varchar(200))
      REMOVE _city_code (varchar(200))
      REMOVE gml_id (buffer)
      REMOVE __is_filepath (buffer)
      REMOVE __is_summary (buffer)
      REMOVE __is_sub_feature (varchar(3))
      REMOVE _feature_types (buffer)
      REMOVE _dict_of_attrs_to_flat (varchar(200))
      REMOVE _flatten_attrs (json)
      REMOVE __is_schema (buffer)
      REMOVE _city_name (buffer)
      REMOVE _feature_type (buffer)
      REMOVE _attributes (json)
    USER_EXPOSED_ATTRIBUTES = city_name
    -> Summary (output)
Summary (output)
AttributeManager_FilePath
    ATTR_TABLE:
      REMOVE _dir_codelists (buffer)
      REMOVE _dir_schemas (buffer)
      REMOVE xml_matched_element (buffer)
      REMOVE xml_fragment (buffer)
      REMOVE xml_id (uint32)
      REMOVE xml_parent_id (uint32)
      REMOVE _num_lod0 (int64)
      REMOVE _num_lod1 (int64)
      REMOVE _num_lod2 (int64)
      REMOVE _num_lod3 (int64)
      REMOVE _num_lod4 (int64)
      REMOVE __add_nsprefix_to_feature_types (varchar(200))
      REMOVE __std_spec_version (varchar(200))
      REMOVE gml_id (buffer)
      REMOVE __is_filepath (buffer)
      REMOVE __is_summary (buffer)
      REMOVE _codelists (json)
      REMOVE _num_features (int64)
      REMOVE __is_sub_feature (varchar(3))
      REMOVE _dict_of_attrs_to_flat (varchar(200))
      REMOVE _num_files (int64)
      REMOVE _flatten_attrs (json)
      REMOVE __is_schema (buffer)
      REMOVE _feature_type (buffer)
      REMOVE _attributes (json)
    USER_EXPOSED_ATTRIBUTES = _suffix,city_name
    -> AttributeKeeper
AttributeKeeper
    CREATE_BULK_MODE_FEATURES = NO
    KEEP_ATTRS = _city_code,_city_name,_feature_types,_folder_package,_folder_root,_gml_filename,_gml_path,_max_lod,_meshcode,_udx_dirs
    -> FilePath (output)
FilePath (output)
AttributeManager_Schema
    ATTR_TABLE:
      REMOVE _folder_root (buffer)
      REMOVE _folder_package (buffer)
      REMOVE _udx_dirs (buffer)
      REMOVE _dir_codelists (buffer)
      REMOVE _dir_schemas (buffer)
      REMOVE _gml_path (buffer)
      REMOVE _gml_filename (buffer)
      REMOVE _meshcode (varchar(200))
      REMOVE xml_matched_element (buffer)
      REMOVE xml_fragment (buffer)
      REMOVE xml_id (uint32)
      REMOVE xml_parent_id (uint32)
      REMOVE _num_lod0 (int64)
      REMOVE _num_lod1 (int64)
      REMOVE _num_lod2 (int64)
      REMOVE _num_lod3 (int64)
      REMOVE _num_lod4 (int64)
      REMOVE __is_sub_feature (varchar(3))
      REMOVE __add_nsprefix_to_feature_types (varchar(200))
      REMOVE __std_spec_version (varchar(200))
      REMOVE _city_code (varchar(200))
      REMOVE _dict_of_attrs_to_flat (varchar(200))
      REMOVE gml_id (buffer)
      REMOVE _max_lod (int16)
      REMOVE _num_files (int64)
      REMOVE _num_features (int64)
      REMOVE __is_filepath (buffer)
      REMOVE __is_summary (buffer)
      REMOVE _feature_types (buffer)
      REMOVE __is_schema (buffer)
      REMOVE _city_name (buffer)
      REMOVE _feature_type (buffer)
      REMOVE _attributes (json)
    USER_EXPOSED_ATTRIBUTES = city_name
    -> Schema (output)
Schema (output)
AttributeManager_Feature
    ATTR_TABLE:
      REMOVE _dir_codelists (buffer)
      REMOVE _dir_schemas (buffer)
      REMOVE xml_matched_element (buffer)
      REMOVE xml_fragment (buffer)
      REMOVE __add_nsprefix_to_feature_types (varchar(200))
      REMOVE __std_spec_version (varchar(200))
      REMOVE _max_lod (int16)
      REMOVE __is_filepath (buffer)
      REMOVE __is_summary (buffer)
      REMOVE _num_features (int64)
      REMOVE _codelists (json)
      REMOVE __is_sub_feature (varchar(3))
      REMOVE _feature_types (buffer)
      REMOVE _dict_of_attrs_to_flat (varchar(200))
      REMOVE _num_files (int64)
      REMOVE _flatten_attrs (json)
      REMOVE __is_schema (buffer)
    USER_EXPOSED_ATTRIBUTES = _folder_root,_folder_package,_udx_dirs,_dir_codelists,_dir_schemas,_gml_path,_gml_filename,_meshcode,xml_matched_element,xml_fragment,xml_id,xml_parent_id,_num_lod0,_num_lod1,_num_lod2,_num_lod3,_num_lod4,__add_nsprefix_to_feature_types,__except_feature_types,__std_spec_version,__extract_dm_geometry_as_xml_fragment,_city_code,gml_id,_city_name,_attributes,_feature_type,_max_lod,__is_filepath,__is_summary
    -> AttributeFeature (output)
AttributeFeature (output)

FME custom transformer PLATEAU4.FolderAndFilePathReader

Parameters:
- DATA_FILE =   # 3D都市モデルデータセット
- GRP_OPTIONS =   # オプション
- TARGET_PACKAGES =   # 対象とするパッケージ
- PARAMETER =   # 対象とするパッケージ (bldg, tran など) が複数あるときはカンマ区切りで列挙, 任意のパッケージを対象とするときは空欄のままとする。
- CODELISTS_FOLDER =   # codelists フォルダー
- SCHEMAS_FOLDER =   # schemas フォルダー

Initiator (input)
    -> FilePathExtractor [Initiator]
FilePathExtractor
    EXTRACT_ARCHIVES = Yes
    SOURCE_DATASET = $(DATA_FILE)
    -> Tester
Tester
    BOOL_OP = OR
    TEST_CLAUSE = TEST @Value(_path_extension) = gml
    TEST_MODE = TEST
    PASSED -> AttributeManager
AttributeManager
    ATTR_TABLE:
      RENAME_SET_VALUE _path_unix > _gml_path (buffer)
      RENAME_SET_VALUE _path_filename > _gml_filename (buffer)
      REMOVE _path_windows (buffer)
      REMOVE _path_rootname (buffer)
      REMOVE _path_extension (buffer)
      REMOVE _path_directory_unix (buffer)
      REMOVE _path_directory_windows (buffer)
    USER_EXPOSED_ATTRIBUTES = _index
    -> PLATEAU4.UDXFolderExtractor
PLATEAU4.UDXFolderExtractor
    CITYGML_FILE = @Value(_gml_path)
    CODELISTS_FOLDER = $(CODELISTS_FOLDER)
    SCHEMAS_FOLDER = $(SCHEMAS_FOLDER)
    -> Tester_2
Note: 指定されたパッケージフォルダー内のファイルを選択
Tester_2
    BOOL_OP = OR
    TEST_CLAUSE:
      TEST $(TARGET_PACKAGES) = ""
      TEST @Value(_folder_package) IN $(TARGET_PACKAGES)
    TEST_MODE = TEST
    PASSED -> Counter
    FAILED -> Unmatched (output)
Note: _file_index
Counter
    CNT_ATTR = _file_index
    GROUP_BY = _udx_dirs
    SCOPE = Local
    START = 1
    -> Matched (output)
Matched (output)
Unmatched (output)

FME custom transformer PLATEAU4.UDXFolderExtractor

Parameters:
- CITYGML_FILE =   # CityGML File (*.gml)
- GRP_OPTIONS =   # Options
- CODELISTS_FOLDER =   # codelists Folder
- SCHEMAS_FOLDER =   # schemas Folder

Input (input)
    -> ParameterFetcher
Note: 2024年度標準製品仕様書第4.0版対応 / パッケージフォルダー名として次のふたつを追加 / ext : 拡張製品仕様書で追加した地物を格納するフォルダー。 / rfld : 災害リスク（浸水）モデルのうち、ため以下ハザードマップを格納するフォルダー。ハザードマップごとにサブフォルダーを作成する。
ParameterFetcher
    ATTR_LIST = __gml_path $(CITYGML_FILE) __codelists_folder $(CODELISTS_FOLDER) __schemas_folder $(SCHEMAS_FOLDER)
    -> PythonCaller
PythonCaller
    NEW_ATTRIBUTES = _folder_root _folder_package _folder_admin _folder_area _udx_dirs _dir_root _dir_codelists _dir_schemas _is_valid_package_name
    PYTHONSOURCE:
      import fme
      import fmeobjects, os, shutil

      # 2024-07-02 サポートするパッケージフォルダー名を追加（ext, rfld）

      PKG_FOLDERS = [
          'area', 'bldg', 'brid', 'cons', 'dem',
          'fld',  'frn',  'gen',  'htd',  'ifld',
          'lsld', 'luse', 'rwy',  'squr', 'tnm',
          'tran', 'trk',  'tun',  'ubld', 'urf',
          'unf',  'veg',  'wtr',  'wwy',
          'ext',  'rfld', #2024年度標準製品仕様書v4.0で追加
      ]

      class PlateauDirectoryParser(object):
          def __init__(self):
              self.pkg_folders = set(PKG_FOLDERS)

          def input(self, feature):
              path = feature.getAttribute('__gml_path').replace('\\', '/')
              folders = path.split('/')
              root, pkg, admin, area, dirs = '', '', '', '', ''
              rtdir = ''
              if folders[-2] in self.pkg_folders:
                  root = folders[-4]
                  pkg = folders[-2]
                  dirs = folders[-2]
                  rtdir = '/'.join(folders[:-3])
              elif folders[-3] in self.pkg_folders:
                  root = folders[-5]
                  pkg = folders[-3]
                  area = folders[-2]
                  dirs ='%s/%s' % (pkg, area)
                  rtdir = '/'.join(folders[:-4])
              elif folders[-4] in self.pkg_folders:
                  root = folders[-6]
                  pkg = folders[-4]
                  admin = folders[-3]
                  area = folders[-2]
                  dirs = '%s/%s/%s' % (pkg, admin, area)
                  rtdir = '/'.join(folders[:-5])
              else:
                  pass

              dir_codelists = rtdir + '/codelists'
              dir_schemas = rtdir + '/schemas'
              if pkg in self.pkg_folders:
                  if not os.path.exists(dir_codelists):
                      dir = feature.getAttribute('__codelists_folder')
                      if os.path.exists(dir):
                          shutil.copytree(dir, dir_codelists)
                  if not os.path.exists(dir_schemas):
                      dir = feature.getAttribute('__schemas_folder')
                      if os.path.exists(dir):
                          shutil.copytree(dir, dir_schemas)

              attrib = {
                  '_folder_root' : root,
                  '_folder_package' : pkg,
                  '_folder_admin' : admin,
                  '_folder_area' : area,
                  '_udx_dirs' : dirs,
                  '_dir_root' : rtdir,
                  '_dir_codelists' : dir_codelists,
                  '_dir_schemas' : dir_schemas,
                  '_is_valid_package_name' : 'Yes' if pkg in self.pkg_folders else 'No',
              }
              for k, v in attrib.items():
                  feature.setAttribute(k, v)

              print(attrib)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = PlateauDirectoryParser
    -> Tester
Tester
    BOOL_OP = OR
    TEST_CLAUSE = TEST @Value(_is_valid_package_name) = Yes
    TEST_MODE = TEST
    PASSED -> AttributeManager
    FAILED -> AttributeManager_2
AttributeManager
    ATTR_TABLE:
      REMOVE __gml_path (buffer)
      REMOVE _is_valid_package_name (buffer)
      REMOVE __codelists_folder (buffer)
      REMOVE __schemas_folder (buffer)
    -> Output (output)
Output (output)
AttributeManager_2
    ATTR_TABLE:
      REMOVE __gml_path (buffer)
      REMOVE _is_valid_package_name (buffer)
      SET_TO fme_rejection_code (varchar(200)) = INVALID_PACKAGE_FOLDER
      REMOVE __codelists_folder (buffer)
      REMOVE __schemas_folder (buffer)
    -> <Rejected> (output)
<Rejected> (output)

FME custom transformer PLATEAU4.LODSplitterWithDm_v2
DMジオメトリを抽出する機能は、CityGMLリーダーの Max Attributes Per Nested Attribute を 1 に設定してDM属性をXML要素として読み込む場合に有効となる。

Parameters:
- FME_PROCESS_GROUP_BY =   # "" Group By
- FME_PROCESS_GROUPS_ORDERED = No   # When All Features Received,No%When Group Changes (Advanced),Yes Complete Groups
- JSON_ATTRIBUTES =   # JSON Attributes
- DEST_COODSYS =   # Destination Coordinate System
- SRS_AXIS_ORDER_DISPLAY = 2,1,3   # GML SRS Axis Order for DM Geometry

Input (input)
    -> Counter
Note: DMジオメトリを抽出する機能は、CityGMLリーダーの Max Attributes Per Nested Attribute を 1 に設定してDM属性をXML要素として読み込む場合に有効
Counter
    CNT_ATTR = __temp_index
    SCOPE = Local
    START = 0
    -> PythonCaller
Note: DM属性 (XML) 抽出
PythonCaller
    NEW_ATTRIBUTES = _dm_attributes_xml
    PYTHONSOURCE:
      import fme
      import fmeobjects, re

      class DmAttributeExtractor(object):
          def __init__(self):
              pass

          def input(self, feature):
              dmAttrs = []
              for attr in feature.getAllAttributeNames():
                  if re.match(r'^uro_.+?_dm_attribute\{\d+\}$', attr):
                      dmAttrs.append(feature.getAttribute(attr))
              if dmAttrs:
                  coordSys = feature.getCoordSys()
                  dmFeature = feature.cloneAttributes()
                  dmFeature.setCoordSys(coordSys)
                  for attr in dmAttrs:
                      dmFeature.setAttribute('_dm_attributes_xml', attr)
                      self.pyoutput(dmFeature)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAttributeExtractor
    -> TestFilter
TestFilter
    DEFAULT_VALUE = <UNFILTERED>
    PASSED_TEST_GROUP_OUTPUT = ALL
    TEST_LIST = "BOOL_OP,OR,COMPOSITE_TEST,""""""1"""""",TEST_CLAUSE,TEST _dm_attributes_xml NOT_ATTRIBUTE_HAS_A_VALUE """,All Features,"BOOL_OP,OR,COMPOSITE_TEST,""""""1"""""",TEST_CLAUSE,TEST _dm_attributes_xml ATTRIBUTE_HAS_A_VALUE """,DM Features
    All Features -> AttributeRemover
    DM Features -> CoordinateSystemExtractor
AttributeRemover
    REMOVE_ATTRS = __temp_index,_dm_attributes_xml
    -> GeometryFilter
GeometryFilter
    FILTER_MODE = COMPLETE
    FILTER_MULTI = FILTER_TYPES]Null]INSTANCES]INSTANCE]FME_CONTROLLER_QUERY_FILE]]FME_CONTROLLER_CHOICE]Complete
    Null -> Junction_10
    <UNFILTERED> -> MultipleGeometryFilter
Note: <Undefined>
Junction_10
    -> Junction_11
Note: GeometryFilter : Null
Junction_11
    -> <Undefined> (output)
MultipleGeometryFilter
    CONTAINS -> Deaggregator
    NOT_CONTAINS -> GeometryPropertyExtractor
    <REJECTED> -> GeometryPropertyExtractor
Deaggregator
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    RECURSIVE = No
    SPLIT_COMPOSITES = No
    ATTR_CONFLICT_RES = Use List Attribute Values
    MODE = Flatten One Level
    DEAGGREGATED -> AttributeExposer
GeometryPropertyExtractor
    EXTRACTTYPE = EXTRACT_GEOMNAME
    GEOM_NAME_FIELD = _geometry_name
    GQUERY:
      for $geom in //geometry
      where $geom/count(parent::geometry) = 0
      return number($geom/@fme_id)
    EXTRACTTYPE_PARAM = Geometry Name
    EXTRACTED -> AttributeExposer
    UNTOUCHED -> <Rejected> (output)
AttributeExposer
    ATTR_TABLE = citygml_level_of_detail,,citygml_level_of_detail{},
    -> AttributeManager
AttributeManager
    ATTR_TABLE:
      REMOVE fme_rejection_code (buffer)
      SET_TO _lod (varchar(200)) = FME_CONDITIONAL:DEFAULT_VALUE'@Substring(@Value(_geometry_name),3,1)'BOOL_OP;OR;COMPOSITE_TEST;1;TEST citygml_level_of_detail ATTRIBUTE_HAS_A_VALUE _FME_BLANK_STRING_'@Value(citygml_level_of_detail)'FME_NUM_CONDITIONS2___
      REMOVE citygml_level_of_detail (varchar(200))
      REMOVE citygml_level_of_detail{} (varchar(200))
    -> Tester
Tester
    BOOL_OP = OR
    TEST_CLAUSE = TEST $(DEST_COODSYS) != ""
    TEST_MODE = TEST
    PASSED -> CsmapReprojector
    FAILED -> Junction_9
CsmapReprojector
    DEST = $(DEST_COODSYS)
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Junction_9
Junction_9
    -> AttributeFilter
AttributeFilter
    ATTR_NAME = _lod
    ATTR_VALUES = 0,1,2,3,4,<Missing>,<Null>,<Empty>,<Unfiltered>
    PRESERVE_FEATURE_ORDER_LOOKUP = PER_OUTPUT_PORT
    0 -> LOD0 (output)
    1 -> LOD1 (output)
    2 -> LOD2 (output)
    3 -> LOD3 (output)
    4 -> LOD4 (output)
    <MISSING> -> <Undefined> (output)
    <NULL> -> <Undefined> (output)
    <EMPTY> -> <Undefined> (output)
    <UNFILTERED> -> <Undefined> (output)
LOD0 (output)
LOD1 (output)
LOD2 (output)
LOD3 (output)
LOD4 (output)
<Undefined> (output)
<Rejected> (output)
CoordinateSystemExtractor
    CRDSYS_ATTR = _coordsys
    -> GeometryRemover
GeometryRemover
    REMOVE_COORDSYS = No
    -> XMLXQueryExtractor
XMLXQueryExtractor
    NEW_ATTRIBUTES = _dm_feature_type _geometry_name
    QUERY_EXPR:
      declare namespace uro="https://www.geospatial.jp/iur/uro/3.1";
      for $x in (//uro:lod0Geometry, //uro:lod0AnchorPoint)
      return (
          fme:set-attribute('_dm_feature_type', local-name($x/parent::node())),
          fme:set-attribute('_geometry_name', local-name($x)),
          $x
      )
    RESULT_ATTRIBUTE = __geometry
    RESULT_TYPE = STRING
    WRITE_XML_HEADER = No
    XML_ATTR = _dm_attributes_xml
    XML_REMOVE_SOURCE_ATTR = No
    XML_TYPE = Attribute specifying XML
    XQUERY_TYPE = XQuery expression
    RESULT_TYPE_NAME = Single value
    QUERY_RESULTS -> PythonCaller_2
Note: DmGeometricAttribute, DmAnnotation 別のインデクス設定
PythonCaller_2
    GROUP_BY = __temp_index
    NEW_ATTRIBUTES = __dm_index
    PYTHONSOURCE:
      import fme
      import fmeobjects

      class DmAttributeIndexer(object):
          def __init__(self):
              self.indexG = 0 # DmGeometricAttribute
              self.indexA = 0 # DmAnnotation
              self.features = []

          def input(self, feature):
              t = feature.getAttribute('_dm_feature_type')
              if t == 'DmGeometricAttribute':
                  feature.setAttribute('__dm_index', self.indexG)
                  self.indexG += 1
              elif t == 'DmAnnotation':
                  feature.setAttribute('__dm_index', self.indexA)
                  self.indexA += 1
              self.features.append(feature)

          def process_group(self):
              for feature in self.features:
                  self.pyoutput(feature)
              self.__init__()

          def close(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAttributeIndexer
    -> Tester_2
Tester_2
    BOOL_OP = OR
    TEST_CLAUSE = TEST @Value(__geometry) TYPE XML
    TEST_MODE = TEST
    PASSED -> GeometryReplacer
    FAILED -> AttributeManager_5
GeometryReplacer
    KIND = GML
    REMOVE_ATTRIBUTE = No
    SOURCE = @Value(__geometry)
    SRS_AXIS_ORDER_DISPLAY = $(SRS_AXIS_ORDER_DISPLAY)
    KIND_LONG = GML
    -> GeometryRefiner
GeometryRefiner
    -> 2DForcer
2DForcer
    2D -> Tester_3
Tester_3
    BOOL_OP = AND
    TEST_CLAUSE:
      TEST $(DEST_COODSYS) != ""
      TEST _coordsys ATTRIBUTE_HAS_A_VALUE ""
    TEST_MODE = TEST
    PASSED -> CsmapReprojector_2
    FAILED -> CoordinateSystemSetter
CsmapReprojector_2
    DEST = $(DEST_COODSYS)
    INTERPOLATION_TYPE = ,NearestNeighbor
    RASTER_CELL_SIZE_LOOKUP = ,PreserveCells
    RASTER_TOLERANCE = 0.0
    SOURCE = @Value(_coordsys)
    INTERPOLATION_TYPE_NAME = Nearest Neighbor
    RASTER_CELL_SIZE = Preserve Cells
    REPROJECTED -> AttributeManager_2
CoordinateSystemSetter
    COORDSYS = @Value(_coordsys)
    -> AttributeManager_2
AttributeManager_2
    ATTR_TABLE:
      SET_TO _lod (varchar(200)) = 0
      REMOVE __geometry (buffer)
      REMOVE _coordsys (buffer)
    USER_EXPOSED_ATTRIBUTES = uro_frn_dm_attribute
    -> AttributeFilter_2
AttributeFilter_2
    ATTR_NAME = _dm_feature_type
    ATTR_VALUES = DmGeometricAttribute,DmAnnotation,<Empty>,<Missing>,<Null>,<Unfiltered>
    PRESERVE_FEATURE_ORDER_LOOKUP = PER_OUTPUT_PORT
    DmGeometricAttribute -> JSONExtractor
    DmAnnotation -> JSONExtractor_2
JSONExtractor
    EXTRACT_QUERY_TABLE = _dm_attributes_json json["uro:DmGeometricAttribute"][@Value(__dm_index)]
    JSON_DOCUMENT = $(JSON_ATTRIBUTES)
    READ_FROM_FILE = NO
    EVALUATED -> PythonCaller_3
PythonCaller_3
    NEW_ATTRIBUTES = dm_dmCode dm_dmCode_code dm_geometryType dm_geometryType_code dm_mapLevel dm_mapLevel_code dm_shapeType dm_shapeType_code
    PYTHONSOURCE:
      import fme
      import fmeobjects, json

      ATTRS = [
          'uro:dmCode',
          'uro:dmCode_code',
          'uro:geometryType',
          'uro:geometryType_code',
          'uro:mapLevel',
          'uro:mapLevel_code',
          'uro:shapeType',
          'uro:shapeType_code',
      ]

      class DmGeometricAttributeExtractor(object):
          def __init__(self):
              pass

          def input(self, feature):
              d = feature.getAttribute('_dm_attributes_json')
              if d:
                  attrib = {}
                  d = json.loads(d)
                  for attr in ATTRS:
                      attrib[attr] = d.get(attr, None)
                  for attr, value in attrib.items():
                      if value != None:
                          feature.setAttribute(attr.replace('uro:', 'dm_'), value)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmGeometricAttributeExtractor
    -> AttributeManager_3
AttributeManager_3
    ATTR_TABLE:
      RENAME_SET_VALUE _dm_feature_type > dm_feature_type (buffer)
      RENAME_SET_VALUE _dm_attributes_xml > dm_attributes_xml (buffer)
      RENAME_SET_VALUE _dm_attributes_json > dm_attributes_json (varchar(200))
      REMOVE __temp_index (int64)
      REMOVE __dm_index (buffer)
    -> Junction_3
Note: DmGeometricAttribute
Junction_3
    -> Junction_4
Junction_4
    -> DmGeometricAttribute (output)
DmGeometricAttribute (output)
JSONExtractor_2
    EXTRACT_QUERY_TABLE = _dm_attributes_json json["uro:DmAnnotation"][@Value(__dm_index)]
    JSON_DOCUMENT = $(JSON_ATTRIBUTES)
    READ_FROM_FILE = NO
    EVALUATED -> PythonCaller_4
PythonCaller_4
    NEW_ATTRIBUTES = dm_dmCode dm_dmCode_code dm_geometryType dm_geometryType_code dm_shapeType dm_shapeType_code dm_label dm_isVertical dm_size dm_orientation dm_linewidth dm_spacing
    PYTHONSOURCE:
      import fme
      import fmeobjects, json

      ATTRS = [
          'uro:dmCode',
          'uro:dmCode_code',
          'uro:geometryType',
          'uro:geometryType_code',
          'uro:shapeType',
          'uro:shapeType_code',
          'uro:label',
          'uro:isVertical',
          'uro:size',
          'uro:orientation',
          'uro:linewidth',
          'uro:spacing'
      ]

      class DmAnnotationExtractor(object):
          def __init__(self):
              pass

          def input(self, feature):
              d = feature.getAttribute('_dm_attributes_json')
              if d:
                  attrib = {}
                  d = json.loads(d)
                  for attr in ATTRS:
                      attrib[attr] = d.get(attr, None)
                  for attr, value in attrib.items():
                      if value != None:
                          feature.setAttribute(attr.replace('uro:', 'dm_'), value)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAnnotationExtractor
    -> AttributeManager_4
AttributeManager_4
    ATTR_TABLE:
      RENAME_SET_VALUE _dm_feature_type > dm_feature_type (buffer)
      RENAME_SET_VALUE _dm_attributes_xml > dm_attributes_xml (buffer)
      RENAME_SET_VALUE _dm_attributes_json > dm_attributes_json (varchar(200))
      REMOVE __temp_index (int64)
      REMOVE __dm_index (buffer)
    -> Junction_5
Note: DmAnnotation
Junction_5
    -> Junction_6
Junction_6
    -> DmAnnotation (output)
DmAnnotation (output)
AttributeManager_5
    ATTR_TABLE:
      REMOVE _geometry_name (buffer)
      REMOVE __geometry (buffer)
      REMOVE _coordsys (buffer)
      REMOVE __temp_index (int64)
      REMOVE __dm_index (buffer)
    USER_EXPOSED_ATTRIBUTES = uro_frn_dm_attribute,_dm_attribute
    -> Junction_7
Note: DmNoGeometry
Junction_7
    -> Junction_8
Junction_8
    -> DmNoGeometry (output)
DmNoGeometry (output)

FME custom transformer TranAreaRefiner

Parameters:
- _LOD = @Value(_lod)   # Lod
- _FEATURE_INDEX = @Value(_feature_index)   # Feature Index

Input (input)
    -> GeometryFilter
GeometryFilter
    FILTER_MODE = SIMPLE
    FILTER_MULTI = FILTER_TYPES]Area]FME_CONTROLLER_QUERY_FILE]]FME_CONTROLLER_CHOICE]Simple
    Area -> Dissolver
    <UNFILTERED> -> Junction_21
Dissolver
    ACCUM_INPUT_ATTRS = Use Attributes From One Feature
    CLEANING_TOLERANCE_LOOKUP = AUTO
    CONNECT_Z_MODE_LOOKUP = FIRST_WINS
    DEAGGREGATE_INPUT = Yes
    GROUP_BY = _feature_index _lod
    CLEANING_TOLERANCE = Automatic
    CONNECT_Z_MODE = First Wins
    AREA -> Aggregator
Aggregator
    ACCUM_ATTRS_NAME = Use Attributes From One Feature
    AGGREGATE_TYPE = Homogeneous Collection (If Possible)
    GROUP_BY = _feature_index _lod
    MODE = Geometry - Assemble One Level
    SEP = ,
    AGGREGATE -> GeometryRefiner
GeometryRefiner
    -> Junction_21
Junction_21
    -> Output (output)
Output (output)
