FME workspace fn002_属性値をデータベースに格納.fmw

Parameters:
- DestDataset_POSTGRES = PostgreSQL_echigo_simulation   # Connection
- SourceDataset_XLSXR_3 = $(FME_MF_DIR)sources/テーブル_長寿命化計画対象施設.xlsx   # Source Microsoft Excel File(s)
- SourceDataset_CSV2_3 = $(FME_MF_DIR)sources/FN001output/**/*_attribute.csv   # Source CSV (Comma Separated Value) File(s)
- SourceDataset_CSV2 = $(FME_MF_DIR)sources/FN001output/unf/*_attribute.csv   # Source CSV (Comma Separated Value) File(s)

Readers:
- XLSXR_2: XLSXR from $(SourceDataset_XLSXR_3)
- CSV2_1: CSV2 from $(SourceDataset_CSV2)
- CSV2_2: CSV2 from $(SourceDataset_CSV2_3)

Writers:
- POSTGRES_1: POSTGRES to $(DestDataset_POSTGRES)

公園施設長寿命化計画対象（R6年度全体） (reader XLSXR_2)
    attributes: gml:id char(41), 公園コード char(3), 公園名 char(24), 公園種別 char(6), 施設コード char(7), 公園施設種類【選択】 char(15), 公園施設名【選択】 char(21), 公園施設名（任意） char(48), 具体的施設名称 char(63), 数量（数値） number(7,1), 数量（単位【選択】) char(3), 規模 char(11), 主要部材【選択】 char(18), 主要部材（任意） char(39), 設置年度 number(4,0), 経過年数 number(2,0), 処分制限期間など number(2,0), 使用見込み期間 number(2,0), 健全度調査以前に実施した補修の有無（有無） char(1), 健全度調査以前に実施した補修の有無（年度） char(1), 健全度調査（年度） number(4,0), 健全度調査（劣化状況） char(285), 健全度調査（健全度） char(3), 健全度調査（緊急度） char(3), 管理類型 char(6), 対策を踏まえた更新見込み年度 number(4,0), 対策費用・2020年（千円） number(5,0), 対策内容・2020年 char(21), 対策費用・2021年（千円） number(6,0), 対策内容・2021年 char(21),
      対策費用・2022年（千円） number(6,0), 対策内容・2022年 char(21), 対策費用・2023年（千円） number(6,0), 対策内容・2023年 char(21), 対策費用・2024年（千円） number(6,0), 対策内容・2024年 char(39), 対策費用・2025年（千円） number(6,0), 対策内容・2025年 char(21), 対策費用・2026年（千円） number(6,0), 対策内容・2026年 char(21), 対策費用・2027年（千円） number(6,0), 対策内容・2027年 char(21), 対策費用・2028年（千円） number(5,0), 対策内容・2028年 char(21), 対策費用・2029年（千円） number(6,0), 対策内容・2029年 char(39), 長寿命化に向けた特記事項 char(96)
    -> AttributeRenamer_2
AttributeRenamer_2
    ATTR_TABLE = RENAME_SET_DEFAULT gml:id > gml_id
    KEEP_RENAMED_ONLY = no
    MISSING_INPUT_ATTRS = REMOVE
    -> Tester_2
Tester_2
    BOOL_OP = AND
    TEST_CLAUSE:
      TEST gml_id NOT_ATTRIBUTE_HAS_A_VALUE ""
      TEST @Value(施設コード) != KAN0569
    TEST_MODE = TEST
    PASSED -> Counter
Counter
    CNT_ATTR = _count
    DOMAIN = counter
    SCOPE = Global
    START = 0
    -> StringFormatter
StringFormatter
    FORMAT = 06s
    SRC_ATTRS = _count
    -> AttributeManager_3
AttributeManager_3
    ATTR_TABLE = SET_TO facility_number (varchar(200)) = bla@Value(_count)
    -> AttributeRenamer_3
CSV (reader CSV2_2)
    attributes: gml_id varchar(255), facility_number varchar(9), 公園コード varchar(3), 公園名 varchar(24), 公園種別 varchar(6), 施設コード varchar(7), 公園施設種類【選択】 varchar(255), 公園施設名【選択】 varchar(255), 公園施設名（任意） varchar(255), 具体的施設名称 varchar(255), 数量（数値） varchar(255), 数量（単位【選択】) varchar(3), 規模 varchar(255), 主要部材【選択】 varchar(255), 主要部材（任意） varchar(255), 設置年度 uint32, 経過年数 uint32, 処分制限期間など uint32, 使用見込み期間 uint32, 健全度調査以前に実施した補修の有無（有無） varchar(1), 健全度調査以前に実施した補修の有無（年度） varchar(1), 健全度調査（年度） uint32, 健全度調査（劣化状況） varchar(255), 健全度調査（健全度） varchar(3), 健全度調査（緊急度） varchar(3), 管理類型 varchar(6), 対策を踏まえた更新見込み年度 uint32, 対策費用・2020年（千円） varchar(255), 対策内容・2020年 varchar(255), 対策費用・2021年（千円） varchar(255),
      対策内容・2021年 varchar(255), 対策費用・2022年（千円） varchar(255), 対策内容・2022年 varchar(255), 対策費用・2023年（千円） varchar(255), 対策内容・2023年 varchar(255), 対策費用・2024年（千円） uint32, 対策内容・2024年 varchar(255), 対策費用・2025年（千円） varchar(255), 対策内容・2025年 varchar(255), 対策費用・2026年（千円） varchar(255), 対策内容・2026年 varchar(255), 対策費用・2027年（千円） varchar(255), 対策内容・2027年 varchar(255), 対策費用・2028年（千円） varchar(255), 対策内容・2028年 varchar(255), 対策費用・2029年（千円） varchar(255), 対策内容・2029年 varchar(255), 長寿命化に向けた特記事項 varchar(255), AR varchar(14), データが作成された日 date, 上流側管底高(m) real32, 下流側管底高(m) real32, 人孔上部レベル(m) real32, 人孔内高(mm) uint32, 人孔底部レベル(m) real32, 内径(mm) uint32, 内径B(mm) uint32, 内径H(mm) uint32, 円形人孔内径(mm) uint32, 土被り(m) real32,
      地下埋設物等施設ID varchar(1), 外径(mm) uint32, 外径B(mm) uint32, 外径H(mm) uint32, 工事年度(西暦) uint32, 工事番号 varchar(9), 延長(m) real32, 推定判別_上流側管底高 uint32, 推定判別_下流側管底高 uint32, 推定判別_人孔上部レベル uint32, 推定判別_人孔内高 uint32, 推定判別_人孔底部レベル uint32, 推定判別_内径 uint32, 推定判別_円形人孔内径 uint32, 推定判別_土被り uint32, 推定判別_外径 uint32, 推定判別_延長 uint32, 推定判別_最大土被り uint32, 推定判別_最小土被り uint32, 推定判別_角型人孔短辺サイズ uint32, 推定判別_角型人孔長辺サイズ uint32, 最大土被り(m) real32, 最小土被り(m) real32, 条数 varchar(6), 管種【任意】 varchar(49), 管種【選択】 varchar(9), 角型人孔短辺サイズ(mm) uint32, 角型人孔長辺サイズ(mm) uint32, 設備種別【任意】 varchar(40), 設備種別【選択】 varchar(15),
      識別名称 varchar(21)
    -> Tester
Tester
    BOOL_OP = OR
    TEST_CLAUSE = CASE_INSENSITIVE_TEST @Value(gml_id) CONTAINS unf
    TEST_MODE = CASE_INSENSITIVE_TEST
    FAILED -> AttributeRenamer_3
AttributeRenamer_3
    ATTR_TABLE:
      RENAME_SET_DEFAULT gml_id
      RENAME_SET_DEFAULT 公園コード > park_code
      RENAME_SET_DEFAULT 公園名 > park_name
      RENAME_SET_DEFAULT 公園種別 > park_type
      RENAME_SET_DEFAULT 施設コード > facility_code
      RENAME_SET_DEFAULT 公園施設種類【選択】 > facility_type
      RENAME_SET_DEFAULT 公園施設名【選択】 > facility_name
      RENAME_SET_DEFAULT 公園施設名（任意） > facility_name_optional
      RENAME_SET_DEFAULT 具体的施設名称 > specific_facility_name
      RENAME_SET_DEFAULT 数量（数値） > quantity_numeric
      RENAME_SET_DEFAULT 数量（単位【選択】) > quantity_unit_choice
      RENAME_SET_DEFAULT 規模 > size
      RENAME_SET_DEFAULT 主要部材【選択】 > main_material
      RENAME_SET_DEFAULT 主要部材（任意） > main_material_optional
      RENAME_SET_DEFAULT 設置年度 > installation_year
      RENAME_SET_DEFAULT 経過年数 > elapsed_years
      RENAME_SET_DEFAULT 処分制限期間など > disposal_limit_period
      RENAME_SET_DEFAULT 使用見込み期間 > expected_usage_period
      RENAME_SET_DEFAULT 健全度調査以前に実施した補修の有無（有無） > repairs_before_healthcheck_exists
      RENAME_SET_DEFAULT 健全度調査以前に実施した補修の有無（年度） > repairs_before_healthcheck_year
      RENAME_SET_DEFAULT 健全度調査（年度） > health_check_year
      RENAME_SET_DEFAULT 健全度調査（劣化状況） > health_check_deterioration_status
      RENAME_SET_DEFAULT 健全度調査（健全度） > health_check_condition
      RENAME_SET_DEFAULT 健全度調査（緊急度） > health_check_urgency
      RENAME_SET_DEFAULT 管理類型 > management_type
      RENAME_SET_DEFAULT 対策を踏まえた更新見込み年度 > updated_year_with_measures
      RENAME_SET_DEFAULT 対策費用・2020年（千円） > cost_2020_thousand_yen
      RENAME_SET_DEFAULT 対策内容・2020年 > content_2020
      RENAME_SET_DEFAULT 対策費用・2021年（千円） > cost_2021_thousand_yen
      RENAME_SET_DEFAULT 対策内容・2021年 > content_2021
      RENAME_SET_DEFAULT 対策費用・2022年（千円） > cost_2022_thousand_yen
      RENAME_SET_DEFAULT 対策内容・2022年 > content_2022
      RENAME_SET_DEFAULT 対策費用・2023年（千円） > cost_2023_thousand_yen
      RENAME_SET_DEFAULT 対策内容・2023年 > content_2023
      RENAME_SET_DEFAULT 対策費用・2024年（千円） > cost_2024_thousand_yen
      RENAME_SET_DEFAULT 対策内容・2024年 > content_2024
      RENAME_SET_DEFAULT 対策費用・2025年（千円） > cost_2025_thousand_yen
      RENAME_SET_DEFAULT 対策内容・2025年 > content_2025
      RENAME_SET_DEFAULT 対策費用・2026年（千円） > cost_2026_thousand_yen
      RENAME_SET_DEFAULT 対策内容・2026年 > content_2026
      RENAME_SET_DEFAULT 対策費用・2027年（千円） > cost_2027_thousand_yen
      RENAME_SET_DEFAULT 対策内容・2027年 > content_2027
      RENAME_SET_DEFAULT 対策費用・2028年（千円） > cost_2028_thousand_yen
      RENAME_SET_DEFAULT 対策内容・2028年 > content_2028
      RENAME_SET_DEFAULT 対策費用・2029年（千円） > cost_2029_thousand_yen
      RENAME_SET_DEFAULT 対策内容・2029年 > content_2029
      RENAME_SET_DEFAULT 長寿命化に向けた特記事項 > note_for_longevity
    KEEP_RENAMED_ONLY = no
    MISSING_INPUT_ATTRS = REMOVE
    -> AttributeManager_2
AttributeManager_2
    ATTR_TABLE:
      REMOVE AR (varchar(14))
      REMOVE データが作成された日 (date)
      REMOVE 上流側管底高(m) (real32)
      REMOVE 下流側管底高(m) (real32)
      REMOVE 人孔上部レベル(m) (real32)
      REMOVE 人孔内高(mm) (uint32)
      REMOVE 人孔底部レベル(m) (real32)
      REMOVE 内径(mm) (uint32)
      REMOVE 内径B(mm) (uint32)
      REMOVE 内径H(mm) (uint32)
      REMOVE 円形人孔内径(mm) (uint32)
      REMOVE 土被り(m) (real32)
      REMOVE 地下埋設物等施設ID (varchar(1))
      REMOVE 外径(mm) (uint32)
      REMOVE 外径B(mm) (uint32)
      REMOVE 外径H(mm) (uint32)
      REMOVE 工事年度(西暦) (uint32)
      REMOVE 工事番号 (varchar(9))
      REMOVE 延長(m) (real32)
      REMOVE 推定判別_上流側管底高 (uint32)
      REMOVE 推定判別_下流側管底高 (uint32)
      REMOVE 推定判別_人孔上部レベル (uint32)
      REMOVE 推定判別_人孔内高 (uint32)
      REMOVE 推定判別_人孔底部レベル (uint32)
      REMOVE 推定判別_内径 (uint32)
      REMOVE 推定判別_円形人孔内径 (uint32)
      REMOVE 推定判別_土被り (uint32)
      REMOVE 推定判別_外径 (uint32)
      REMOVE 推定判別_延長 (uint32)
      REMOVE 推定判別_最大土被り (uint32)
      REMOVE 推定判別_最小土被り (uint32)
      REMOVE 推定判別_角型人孔短辺サイズ (uint32)
      REMOVE 推定判別_角型人孔長辺サイズ (uint32)
      REMOVE 最大土被り(m) (real32)
      REMOVE 最小土被り(m) (real32)
      REMOVE 条数 (varchar(6))
      REMOVE 管種【任意】 (varchar(49))
      REMOVE 管種【選択】 (varchar(9))
      REMOVE 角型人孔短辺サイズ(mm) (uint32)
      REMOVE 角型人孔長辺サイズ(mm) (uint32)
      REMOVE 設備種別【任意】 (varchar(40))
      REMOVE 設備種別【選択】 (varchar(15))
      REMOVE 識別名称 (varchar(21))
      REMOVE _count (int64)
    -> longlife_facilities_2024 (writer POSTGRES_1)
longlife_facilities_2024 (writer POSTGRES_1)
    attributes: gml_id varchar(255), facility_number varchar(9), park_code varchar(3), park_name varchar(24), park_type varchar(6), facility_code varchar(7), facility_type varchar(255), facility_name varchar(255), facility_name_optional varchar(255), specific_facility_name varchar(255), quantity_numeric varchar(255), quantity_unit_choice varchar(3), size varchar(255), main_material varchar(255), main_material_optional varchar(255), installation_year int8, elapsed_years int8, disposal_limit_period int8, expected_usage_period int8, repairs_before_healthcheck_exists varchar(1), repairs_before_healthcheck_year varchar(1), health_check_year int8, health_check_deterioration_status varchar(255), health_check_condition varchar(3), health_check_urgency varchar(3), management_type varchar(6), updated_year_with_measures int8, cost_2020_thousand_yen varchar(255), content_2020 varchar(255), cost_2021_thousand_yen varchar(255),
      content_2021 varchar(255), cost_2022_thousand_yen varchar(255), content_2022 varchar(255), cost_2023_thousand_yen varchar(255), content_2023 varchar(255), cost_2024_thousand_yen int8, content_2024 varchar(255), cost_2025_thousand_yen varchar(255), content_2025 varchar(255), cost_2026_thousand_yen varchar(255), content_2026 varchar(255), cost_2027_thousand_yen varchar(255), content_2027 varchar(255), cost_2028_thousand_yen varchar(255), content_2028 varchar(255), cost_2029_thousand_yen varchar(255), content_2029 varchar(255), note_for_longevity varchar(255)
CSV (reader CSV2_1)
    attributes: gml_id varchar(40), facility_number varchar(9), 地下埋設物等施設ID varchar(1), 識別名称 varchar(21), 設備種別【選択】 varchar(15), 設備種別【任意】 varchar(40), 管種【選択】 varchar(9), 管種【任意】 varchar(49), 土被り(m) real32, 推定判別_土被り uint32, 最大土被り(m) real32, 推定判別_最大土被り uint32, 最小土被り(m) real32, 推定判別_最小土被り uint32, 上流側管底高(m) real32, 推定判別_上流側管底高 uint32, 下流側管底高(m) real32, 推定判別_下流側管底高 uint32, 延長(m) real32, 推定判別_延長 uint32, 内径(mm) uint32, 推定判別_内径 uint32, 外径(mm) uint32, 推定判別_外径 uint32, 内径B(mm) uint32, 内径H(mm) uint32, 外径B(mm) uint32, 外径H(mm) uint32, 条数 varchar(6), 角型人孔長辺サイズ(mm) uint32,
      推定判別_角型人孔長辺サイズ uint32, 角型人孔短辺サイズ(mm) uint32, 推定判別_角型人孔短辺サイズ uint32, 円形人孔内径(mm) uint32, 推定判別_円形人孔内径 uint32, 人孔底部レベル(m) real32, 推定判別_人孔底部レベル uint32, 人孔上部レベル(m) real32, 推定判別_人孔上部レベル uint32, 人孔内高(mm) uint32, 推定判別_人孔内高 uint32, 工事年度(西暦) uint32, 工事番号 varchar(9), データが作成された日 date, AR varchar(14)
    -> AttributeRenamer
AttributeRenamer
    ATTR_TABLE:
      RENAME_SET_DEFAULT gml_id
      RENAME_SET_DEFAULT 地下埋設物等施設ID > underground_facility_id
      RENAME_SET_DEFAULT 識別名称 > identification_name
      RENAME_SET_DEFAULT 設備種別【選択】 > facility_type_selection
      RENAME_SET_DEFAULT 設備種別【任意】 > facility_type_optional
      RENAME_SET_DEFAULT 管種【選択】 > pipe_type_selection
      RENAME_SET_DEFAULT 管種【任意】 > pipe_type_optional
      RENAME_SET_DEFAULT 土被り(m) > soil_cover_depth_meters
      RENAME_SET_DEFAULT 推定判別_土被り > estimated_soil_cover_depth
      RENAME_SET_DEFAULT 最大土被り(m) > maximum_soil_cover_depth_meters
      RENAME_SET_DEFAULT 推定判別_最大土被り > estimated_maximum_soil_cover_depth
      RENAME_SET_DEFAULT 最小土被り(m) > minimum_soil_cover_depth_meters
      RENAME_SET_DEFAULT 推定判別_最小土被り > estimated_minimum_soil_cover_depth
      RENAME_SET_DEFAULT 上流側管底高(m) > upstream_pipe_bottom_elevation_meters
      RENAME_SET_DEFAULT 推定判別_上流側管底高 > estimated_upstream_pipe_bottom_elevation
      RENAME_SET_DEFAULT 下流側管底高(m) > downstream_pipe_bottom_elevation_meters
      RENAME_SET_DEFAULT 推定判別_下流側管底高 > estimated_downstream_pipe_bottom_elevation
      RENAME_SET_DEFAULT 延長(m) > pipe_length_meters
      RENAME_SET_DEFAULT 推定判別_延長 > estimated_pipe_length
      RENAME_SET_DEFAULT 内径(mm) > inner_diameter_millimeters
      RENAME_SET_DEFAULT 推定判別_内径 > estimated_inner_diameter
      RENAME_SET_DEFAULT 外径(mm) > outer_diameter_millimeters
      RENAME_SET_DEFAULT 推定判別_外径 > estimated_outer_diameter
      RENAME_SET_DEFAULT 内径B(mm) > inner_diameter_b_millimeters
      RENAME_SET_DEFAULT 内径H(mm) > inner_diameter_h_millimeters
      RENAME_SET_DEFAULT 外径B(mm) > outer_diameter_b_millimeters
      RENAME_SET_DEFAULT 外径H(mm) > outer_diameter_h_millimeters
      RENAME_SET_DEFAULT 条数 > number_of_sections
      RENAME_SET_DEFAULT 角型人孔長辺サイズ(mm) > rectangular_manhole_long_side_millimeters
      RENAME_SET_DEFAULT 推定判別_角型人孔長辺サイズ > estimated_rectangular_manhole_long_side
      RENAME_SET_DEFAULT 角型人孔短辺サイズ(mm) > rectangular_manhole_short_side_millimeters
      RENAME_SET_DEFAULT 推定判別_角型人孔短辺サイズ > estimated_rectangular_manhole_short_side
      RENAME_SET_DEFAULT 円形人孔内径(mm) > circular_manhole_inner_diameter_millimeters
      RENAME_SET_DEFAULT 推定判別_円形人孔内径 > estimated_circular_manhole_inner_diameter
      RENAME_SET_DEFAULT 人孔底部レベル(m) > manhole_bottom_level_meters
      RENAME_SET_DEFAULT 推定判別_人孔底部レベル > estimated_manhole_bottom_level
      RENAME_SET_DEFAULT 人孔上部レベル(m) > manhole_top_level_meters
      RENAME_SET_DEFAULT 推定判別_人孔上部レベル > estimated_manhole_top_level
      RENAME_SET_DEFAULT 人孔内高(mm) > manhole_inner_height_millimeters
      RENAME_SET_DEFAULT 推定判別_人孔内高 > estimated_manhole_inner_height
      RENAME_SET_DEFAULT 工事年度(西暦) > construction_year
      RENAME_SET_DEFAULT 工事番号 > construction_code
      RENAME_SET_DEFAULT データが作成された日 > citygml_creation_date
    KEEP_RENAMED_ONLY = no
    MISSING_INPUT_ATTRS = REMOVE
    -> AttributeManager
AttributeManager
    ATTR_TABLE = REMOVE AR (varchar(14))
    -> underground_facilities_2024 (writer POSTGRES_1)
underground_facilities_2024 (writer POSTGRES_1)
    attributes: gml_id varchar(40), facility_number varchar(9), underground_facility_id varchar(1), identification_name varchar(21), facility_type_selection varchar(15), facility_type_optional varchar(40), pipe_type_selection varchar(9), pipe_type_optional varchar(49), soil_cover_depth_meters float4, estimated_soil_cover_depth int8, maximum_soil_cover_depth_meters float4, estimated_maximum_soil_cover_depth int8, minimum_soil_cover_depth_meters float4, estimated_minimum_soil_cover_depth int8, upstream_pipe_bottom_elevation_meters float4, estimated_upstream_pipe_bottom_elevation int8, downstream_pipe_bottom_elevation_meters float4, estimated_downstream_pipe_bottom_elevation int8, pipe_length_meters float4, estimated_pipe_length int8, inner_diameter_millimeters int8, estimated_inner_diameter int8, outer_diameter_millimeters int8, estimated_outer_diameter int8, inner_diameter_b_millimeters int8, inner_diameter_h_millimeters int8, outer_diameter_b_millimeters int8, outer_diameter_h_millimeters int8, number_of_sections varchar(6), rectangular_manhole_long_side_millimeters int8,
      estimated_rectangular_manhole_long_side int8, rectangular_manhole_short_side_millimeters int8, estimated_rectangular_manhole_short_side int8, circular_manhole_inner_diameter_millimeters int8, estimated_circular_manhole_inner_diameter int8, manhole_bottom_level_meters float4, estimated_manhole_bottom_level int8, manhole_top_level_meters float4, estimated_manhole_top_level int8, manhole_inner_height_millimeters int8, estimated_manhole_inner_height int8, construction_year int8, construction_code varchar(9), citygml_creation_date date
