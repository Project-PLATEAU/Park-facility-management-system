FME workspace fn003_OBJ形式を3D Tilesへ変換.fmw

Parameters:
- REQUEST_MESSAGE_JSON:   # Request Message JSON
      {
          "model_url": "http://vrobject.s3.amazonaws.com/obj/DCF-16DA-3D-2410v2024_1.zip",
          "obj_height": 1,
          "obj_id": 12345,
          "obj_lat": 37.428737,
          "obj_lon": 138.747797,
          "obj_name": "test",
          "obj_rotation": 30,
          "request_datetime": "2024-11-22 16:28:32+09:00",
          "request_id": "000",
          "source_format": "obj"
      }
- AMAZONS3_NAMED_CONNECTION = AWS_echigo_simulation   # "Amazon Web Services"%"safe.s3connector.Amazon S3 Compatible Storage" AWS Connection
- SourceDataset_GEOTIFF = $(FME_MF_DIR)resource/越後丘陵公園_地形/越後丘陵公園_数値地形図モデル.tif   # DEM Raster (GeoTIFF)
- DEM_COORDSYS = EPSG:6676   # DEM Coordinate System
- GEOID_HEIGHT_GRID = $(FME_MF_DIR)resource/gsigeo2011/gsigeo2011_ver2_2.gdc   # Geoid Height Grid

Readers:
- GEOTIFF_1: GEOTIFF from $(SourceDataset_GEOTIFF)

Writers:
- AUTOMATIONS_1: AUTOMATIONS

Creator
    GEOMTYPE = Geometry Object
    NUM = 1
    CREATED -> JSONFlattener
GEOTIFF (reader GEOTIFF_1)
    attributes: datatype char(255)
    -> CoordinateSystemSetter_2
Note: OBJデータセット読込
FeatureReader_OBJ
    ATTRIBUTES = "BBF-1401-3D-2410 v2024",
    ATTR_ACCUM_MODE = Merge Initiator and Result
    ATTR_CONFLICT_RES = Use Result
    ATTR_IGNORE_NULLS = No
    COMBINE_GEOM = Use Result
    DATASET = @Value(_model_url)
    FORMAT = OBJ
    GEOMETRY_TYPES = "BBF-1401-3D-2410 v2024",""",fme_collection,fme_line,fme_point,fme_surface"""
    INTERACT = NONE
    OBJ_MERGE_MESH_PARTS = No
    OBJ_MOVE_TO_WORLD_COORDSYS = Yes
    OBJ_USE_SEARCH_ENVELOPE = NO
    OBJ_VARIABLE_FEATURE_TYPES = yes
    ORDER_RESULTS = No
    OUTPUT_ADD_SCHEMA_ATTRIBUTES = NO
    OUTPUT_FEATURES_DISPLAY = Schema and Data Features
    <OTHER> -> Rotator
Note: 回転
Rotator
    ANGLE = @Value(_obj_rotation)
    XORIG = 0
    YORIG = 0
    ROTATED -> BoundsExtractor
BoundsExtractor
    ZMAX = _zmax
    ZMIN = _zmin
    -> ExpressionEvaluator
ExpressionEvaluator
    ACTION = Create New Attribute
    EXPRESSION = @Value(_obj_height)/(@Value(_zmax)-@Value(_zmin))
    VAL_ATTR = _scale
    -> 3DAffiner
Note: スケール及びオフセット
3DAffiner
    A = @Value(_scale)
    B = 0
    C = 0
    D = @Value(_x)
    E = 0
    F = @Value(_scale)
    G = 0
    H = @Value(_y)
    I = 0
    J = 0
    K = @Value(_scale)
    L = @Value(_z)
    AFFINED -> CoordinateSystemSetter
Note: EPSG:3857 設定
CoordinateSystemSetter
    COORDSYS = EPSG:3857
    -> TempPathnameCreator
StringReplacer
    CASE = NO
    FIND_TEXT = s3.ap-northeast-1.amazonaws.com/vrobject
    NO_MATCH = _FME_NO_OP_
    REGEXP = NO
    REPLACE_TEXT = vrobject.s3.amazonaws.com
    SRC_ATTRS = _url
    -> JSONTemplater [ROOT]
JSONTemplater
    RESULT_ATTRIBUTE = result
    ROOT_QUERY_EXPR:
      {
          "obj_type" : 0,
          "obj_elevation" : fme:get-attribute("_obj_elevation"),
          "fme_job_id" : "$(FME_JOB_ID)",
          "fme_result" : true,
          "tileset_url" : fme:get-attribute("_url")||"/tileset.json",
          "removed" : false
      }
    VISIBLE_QUERY_VALIDATE = Yes
    -> success (writer AUTOMATIONS_1)
success (writer AUTOMATIONS_1)
    attributes: result json

Bookmark: パラメーター取得・展開
JSONFlattener
    ERROR_LIST_ATTR = _json_error
    JSON_DOCUMENT = $(REQUEST_MESSAGE_JSON)
    PREFIX_STRING = _
    READ_FROM_FILE = NO
    RECURSIVE = YES
    -> AttributeExposer
AttributeExposer
    ATTR_TABLE = _model_url,varchar(121),_obj_height,uint8,_obj_id,uint16,_obj_lat,real64,_obj_lon,real64,_obj_name,varchar(9),_obj_rotation,uint8,_request_datetime,varchar(25),_request_id,uint8,_source_format,varchar(3)
    -> VertexCreator

Bookmark: 設置位置のポイント作成
VertexCreator
    MEASURE_TYPE_LOOKUP = CONTINUOUS
    MODE = REPLACE
    XVAL = @Value(_obj_lon)
    YVAL = @Value(_obj_lat)
    MEASURE_TYPE = Continuous
    MODE_NAME = Replace with Point
    -> PROJReprojector
PROJReprojector
    DEST = $(DEM_COORDSYS)
    INTERPOLATION_TYPE = ,NearestNeighbor
    RASTER_CELL_SIZE_LOOKUP = ,PreserveCells
    RASTER_TOLERANCE = 0.0
    SOURCE = EPSG:4326
    TRANSFORM_TYPE = Automatic Transformation
    INTERPOLATION_TYPE_NAME = Nearest Neighbor
    RASTER_CELL_SIZE = Preserve Cells
    REPROJECTED -> PointOnRasterValueExtractor [POINT]

Bookmark: 越後DEMから指定地点の標高を取得
CoordinateSystemSetter_2
    COORDSYS = $(DEM_COORDSYS)
    -> PointOnRasterValueExtractor [RASTER]
PointOnRasterValueExtractor
    INTERPOLATION_TYPE = NearestNeighbor
    INTERPOLATION_TYPE_NAME = Nearest Neighbor
    POINT -> AttributeManager
AttributeManager
    ATTR_TABLE:
      SET_TO _x (real64) = @Value(_obj_lon)
      SET_TO _y (real64) = @Value(_obj_lat)
      SET_TO _z (real64) = @Value(_band{0}.value)
      SET_TO _obj_elevation (varchar(200)) = @Value(_band{0}.value)
      REMOVE datatype (varchar(255))
      REMOVE fme_basename (varchar(50))
      REMOVE _band{}.value (real64)
      REMOVE _band{}.palette{}.value (real64)
    -> CsmapAttributeReprojector

Bookmark: EPSG:3857 における座標値設定, z は楕円体高に変換
Note: 3D Tiles ライターにより測地系の変換 (JGD2011-> WGS84) に伴う座標値のシフトが生じないよう、WGS84の座標系 (EPSG:3857) を使用した。
CsmapAttributeReprojector
    DEST = EPSG:3857
    GEOID_HEIGHT_GRID = $(GEOID_HEIGHT_GRID)
    SOURCE = EPSG:4326
    VERTICAL_HANDLING_LOOKUP = 3D_ORTHOMETRIC_TO_ELLIPSOID
    XATTR = _x
    YATTR = _y
    ZATTR = _z
    VERTICAL_HANDLING = Orthometric height -> Geocentric or ellipsoid height
    REPROJECTED -> FeatureReader_OBJ [INITIATOR]

Bookmark: 3D Tiles に変換、作業用の一時ディレクトリに出力
TempPathnameCreator
    PATHNAME_ATTR = _temp_dir
    -> FeatureWriter_3D_Tiles [Output]
FeatureWriter_3D_Tiles
    CESIUM3DTILES_ALLOW_MIXED_GEOM_TILESETS = NO
    CESIUM3DTILES_COORDINATE_SYSTEM_GRANULARITY = FEATURE
    CESIUM3DTILES_CREATE_ATLAS_TEXTURES = YES
    CESIUM3DTILES_DEFAULT_CRS = EPSG:4326
    CESIUM3DTILES_MAX_FACES_PER_TILE = 1000
    CESIUM3DTILES_TEXTURE_FORMAT_CHOICES = WEBP
    DATASET = @Value(_temp_dir)
    DATASET_ATTR = _dataset
    FEATURE_TYPE_LIST_ATTR = _feature_types
    FORMAT = CESIUM3DTILES
    MORE_SUMMARY_ATTRS = _obj_elevation
    TOTAL_FEATURES_WRITTEN_ATTR = _total_features_written
    SUMMARY -> AttributeManager_2

Bookmark: 変換結果を指定されたS3バケット/パスににアップロード
AttributeManager_2
    ATTR_TABLE:
      SET_TO _tiliset (varchar(200)) = @Value(_dataset)/@Value(_feature_types{0}.name)
      REMOVE _feature_types{}.count (uint64)
      REMOVE _feature_types{}.name (buffer)
      REMOVE _dataset (buffer)
      REMOVE _total_features_written (uint64)
      SET_TO _obj_elevation (varchar(200)) = @Value(_feature_types{0}._obj_elevation)
    -> S3Connector
    -> S3Connector_2
S3Connector
    AMAZONS3_NAMED_CONNECTION = $(AMAZONS3_NAMED_CONNECTION)
    CREDENTIAL_SOURCE = Web Connection
    OPERATION_TYPE = Upload
    PARAMETER_SETUP = _FME_SOURCE_TYPE]Folder]_FME_SOURCE_FILE]<Unused>]_FME_SOURCE_FOLDER]@Value(_tiliset)]_FME_INCLUDE_SUBFOLDERS]Yes]_FME_CONTENTS_ONLY]No]_FME_DATA_TO_UPLOAD]<Unused>]_FME_BUCKET][{"display":"vrobject","value":"vrobject"}]]_FME_UPLOAD_DESTINATION_PATH][{"display":"/3d-tiles/ar","value":"3d-tiles/ar/"}]]_FME_UPLOAD_ATTR_FILENAME]<Unused>]_FME_HANDLE_EXISTING_FILE]Overwrite]_FME_S3_ACCELERATION]No]_FME_S3_UPLOAD_ENCRYPTION]None]_FME_S3_CANNED_ACL]public-read]_FME_SIGNED_URL_GENERATE]NO]_FME_SIGNED_URL_EXPIRY_TIME]<Unused>]_FME_METADATA_GROUP]FME_DISCLOSURE_CLOSED]_FME_S3_CUSTOM_HEADERS]<Unused>]_UPLOAD_FME_ATTRIBUTES_TO_ADD]"_name _full_path _bucket_name _url"]FME_CONTROLLER_QUERY_FILE]amazons3_deps1/Upload.fme]FME_CONTROLLER_CHOICE]Upload
    _FME_S3_REQUESTER_PAYS = no
    _FME_S3_VERIFY_SSL = yes
    -> StringReplacer
S3Connector_2
    AMAZONS3_NAMED_CONNECTION = $(AMAZONS3_NAMED_CONNECTION)
    CREDENTIAL_SOURCE = Web Connection
    OPERATION_TYPE = Upload
    PARAMETER_SETUP = _FME_SOURCE_TYPE]Folder]_FME_SOURCE_FILE]<Unused>]_FME_SOURCE_FOLDER]@Value(_tiliset)]_FME_INCLUDE_SUBFOLDERS]Yes]_FME_CONTENTS_ONLY]No]_FME_DATA_TO_UPLOAD]<Unused>]_FME_BUCKET][{"display":"vrobject","value":"vrobject"}]]_FME_UPLOAD_DESTINATION_PATH][{"display":"/3d-tiles/vr/","value":"3d-tiles/vr/"}]]_FME_UPLOAD_ATTR_FILENAME]<Unused>]_FME_HANDLE_EXISTING_FILE]Overwrite]_FME_S3_ACCELERATION]No]_FME_S3_UPLOAD_ENCRYPTION]None]_FME_S3_CANNED_ACL]public-read]_FME_SIGNED_URL_GENERATE]NO]_FME_SIGNED_URL_EXPIRY_TIME]<Unused>]_FME_METADATA_GROUP]FME_DISCLOSURE_CLOSED]_FME_S3_CUSTOM_HEADERS]<Unused>]_UPLOAD_FME_ATTRIBUTES_TO_ADD]"_name _full_path _bucket_name _url"]FME_CONTROLLER_QUERY_FILE]amazons3_deps1/Upload.fme]FME_CONTROLLER_CHOICE]Upload
    _FME_S3_REQUESTER_PAYS = no
    _FME_S3_VERIFY_SSL = yes
