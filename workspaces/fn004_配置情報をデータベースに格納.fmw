FME workspace fn004_配置情報をデータベースに格納.fmw

Parameters:
- REQUEST_MESSAGE_JSON:   # Request Message JSON
      {
      	"model_url": "http://vrobject.s3.amazonaws.com/obj/YUG0001_1.zip",
      	"obj_height": 1,
      	"obj_id": 12345,
      	"obj_lat": 37.428737,
      	"obj_lon": 138.747797,
      	"obj_name": "test",
      	"obj_rotation": 30,
      	"request_datetime": "2024-11-22 16:28:32+09:00",
      	"request_id": "000",
      	"source_format": "obj"
      }
- SUCCESS_MESSAGE_JSON:   # Success Message JSON
      {
          "fme_job_id": "",
          "fme_result": true,
          "obj_elevation": "115.869",
          "obj_type": 0,
          "removed": false,
          "tileset_url": "https://s3.ap-northeast-1.amazonaws.com/vrobject/3d-tiles/test/tileset.json"
      }
- DestDataset_POSTGRES = PostgreSQL_echigo_simulation   # Connection

Writers:
- POSTGRES_1: POSTGRES to $(DestDataset_POSTGRES)

Creator
    GEOMTYPE = Geometry Object
    NUM = 1
    CREATED -> DateTimeStamper
ParameterFetcher
    ATTR_LIST = _REQUEST_MESSAGE_JSON $(REQUEST_MESSAGE_JSON) _SUCCESS_MESSAGE_JSON $(SUCCESS_MESSAGE_JSON)
    -> Tester
Tester
    BOOL_OP = OR
    TEST_CLAUSE = TEST _SUCCESS_MESSAGE_JSON ATTRIBUTE_HAS_A_VALUE ""
    TEST_MODE = TEST
    PASSED -> JSONTemplater [ROOT]
Note: resultにrequestメッセージとsuccessメッセージのjsonを集約
JSONTemplater
    RESULT_ATTRIBUTE = result
    ROOT_QUERY_EXPR:
      {|
          fme:get-json-attribute("_REQUEST_MESSAGE_JSON"),
          fme:get-json-attribute("_SUCCESS_MESSAGE_JSON"),
          {"update_datetime":fme:get-attribute("_timestamp")}
      |}
    VISIBLE_QUERY_VALIDATE = Yes
    -> JSONExtractor
JSONExtractor
    EXTRACT_QUERY_TABLE = uuid json["request_id"]
    JSON_DOCUMENT = @Value(result)
    READ_FROM_FILE = NO
    EVALUATED -> AttributeManager
AttributeManager
    ATTR_TABLE:
      SET_TO status (varchar(4)) = done
      REMOVE _creation_instance (uint64)
      RENAME_SET_VALUE _timestamp > created_at (buffer)
      REMOVE _REQUEST_MESSAGE_JSON (buffer)
      REMOVE _SUCCESS_MESSAGE_JSON (buffer)
    -> relocation_status (writer POSTGRES_1)
relocation_status (writer POSTGRES_1)
    attributes: uuid text, created_at timestamp, deleted_at timestamp, type text, url text, format text, alias text, name text, object_height float8, object_scale float8, result text, status text, error text

Bookmark: 現在時刻を表示
Note: 基準時刻
DateTimeStamper
    DATETIME_ATTR = _timestamp
    INCLUDE_FRAC_SECONDS = NO
    INCLUDE_OFFSET = NO
    STAMP_TYPE = datetime
    TIMEZONE = utc
    -> DateTimeCalculator
Note: 日本時間に修正
DateTimeCalculator
    MODE = DATETIMECALC_1_ADD_INTERVAL
    OPERATION_PARAMETERS = START_DATETIME]@Value(_timestamp)]OPERATOR]ADD]YEARS]0]MONTHS]0]DAYS]0]HOURS]9]MINUTES]0]SECONDS]0]RESULT_DATETIME]_timestamp]FME_CONTROLLER_QUERY_FILE]transformers/dependencies/datetimecalculator/DATETIMECALC_1_ADD_INTERVAL.fme]FME_CONTROLLER_CHOICE]DATETIMECALC_1_ADD_INTERVAL
    -> DateTimeConverter
Note: 表示形式を修正
DateTimeConverter
    DATETIME_ATTR = _timestamp
    OUT_FORMAT = ISO
    PASSTHROUGH = NO
    REPAIR_INPUT = YES
    -> ParameterFetcher
